FME workspace tran_plateau_v23_v200.fmw

Parameters:
- SourceDataset_CITYGML =   # Input CityGML File(s)
- TEMPLATEFILE_GEODATABASE_FILE =   # Template XML Workspace Document (Schema Only)
- DestDataset_GEODATABASE_FILE =   # Output File Geodatabase

Readers:
- TEXTLINE_1: TEXTLINE from $(SourceDataset_CITYGML)
- CITYGML_2: CITYGML from $(SourceDataset_CITYGML)
- GEODATABASE_XML_1: GEODATABASE_XML from $(TEMPLATEFILE_GEODATABASE_FILE)

Writers:
- GEODATABASE_FILE_1: GEODATABASE_FILE to $(DestDataset_GEODATABASE_FILE)

AuxiliaryTrafficArea (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_surface_material xml_buffer, citygml_surface_material_codeSpace xml_buffer, citygml_level_of_detail{} xml_buffer
    -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> ListElementCounter
ListElementCounter
    CNT_ATTR = _lodCnt
    LIST_NAME = citygml_level_of_detail{}
    -> AttributeCreator_2
AttributeCreator_2
    ATTR_TABLE:
      SET_TO tran_function = @Value(citygml_function{0})
      SET_TO _geometory_lod = FME_CONDITIONAL:DEFAULT_VALUE'@Value(citygml_level_of_detail{@sum(@Value(_lodCnt),-1)})'BOOL_OP;OR;COMPOSITE_TEST;1;TEST @Value(_part_number) < @sum(@Value(_lodCnt),-1)'@Value(citygml_level_of_detail{@Value(_part_number)})'FME_NUM_CONDITIONS2___
    -> AttributeManager_2
AttributeManager_2
    ATTR_TABLE:
      RENAME_SET_VALUE gml_id > tran_AuxiliaryTrafficArea_gml_id
      RENAME_SET_VALUE gml_parent_id > tran_Road_gml_id
      REMOVE citygml_target_uri
      REMOVE citygml_feature_role
      REMOVE citygml_feature_role_attr_name
      REMOVE citygml_feature_role_attr_val
      REMOVE gml_description
      REMOVE gml_name
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_class
      REMOVE citygml_class_codeSpace
      REMOVE citygml_function{}
      REMOVE citygml_function{}.codeSpace
      REMOVE citygml_usage{}
      REMOVE citygml_usage{}.codeSpace
      RENAME_SET_VALUE citygml_surface_material > tran_surfaceMaterial
      REMOVE citygml_surface_material_codeSpace
      REMOVE _part_number
    USER_EXPOSED_ATTRIBUTES = OBJECTID,Shape_Length,Shape_Area
    -> TestFilter_AuxiliaryTrafficArea
TestFilter_AuxiliaryTrafficArea
    DEFAULT_VALUE = <UNFILTERED>
    TEST_LIST = "BOOL_OP,OR,COMPOSITE_TEST,""""""1"""""",TEST_CLAUSE,CASE_INSENSITIVE_TEST @Value(_geometory_lod) = 2",lod2_AuxiliaryTrafficArea,"BOOL_OP,OR,COMPOSITE_TEST,""""""1"""""",TEST_CLAUSE,CASE_INSENSITIVE_TEST @Value(_geometory_lod) = 3",lod3_AuxiliaryTrafficArea
    lod2_AuxiliaryTrafficArea -> lod2_AuxiliaryTrafficArea (writer GEODATABASE_FILE_1)
    lod3_AuxiliaryTrafficArea -> lod3_AuxiliaryTrafficArea (writer GEODATABASE_FILE_1)
lod2_AuxiliaryTrafficArea (writer GEODATABASE_FILE_1)
    attributes: tran_AuxiliaryTrafficArea_gml_id char(50), core_creationDate char(10), core_terminationDate char(10), tran_function char(10), tran_surfaceMaterial char(10), tran_Road_gml_id char(50)
lod3_AuxiliaryTrafficArea (writer GEODATABASE_FILE_1)
    attributes: tran_AuxiliaryTrafficArea_gml_id char(50), core_creationDate char(10), core_terminationDate char(10), tran_function char(10), tran_surfaceMaterial char(10), tran_Road_gml_id char(50)
CityModel (reader CITYGML_2)
    attributes: citygml_target_uri xml_buffer, gml_description xml_buffer, gml_name xml_buffer, citygml_city_object_member{}.xlink_href xml_buffer, gml_feature_member{}.xlink_href xml_buffer
TrafficArea (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_surface_material xml_buffer, citygml_surface_material_codeSpace xml_buffer, citygml_level_of_detail{} xml_buffer, uro_traffic_area_structure_attribute{}.uro_traffic_area_structure_attribute_uro_number_of_lanes xml_int64
    -> Deaggregator_3
Deaggregator_3
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> ListElementCounter_2
ListElementCounter_2
    CNT_ATTR = _lodCnt
    LIST_NAME = citygml_level_of_detail{}
    -> AttributeCreator_3
AttributeCreator_3
    ATTR_TABLE:
      SET_TO tran_function = @Value(citygml_function{0})
      SET_TO _geometory_lod = FME_CONDITIONAL:DEFAULT_VALUE'@Value(citygml_level_of_detail{@sum(@Value(_lodCnt),-1)})'BOOL_OP;OR;COMPOSITE_TEST;1;TEST @Value(_part_number) < @sum(@Value(_lodCnt),-1)'@Value(citygml_level_of_detail{@Value(_part_number)})'FME_NUM_CONDITIONS2___
      SET_TO uro_trafficAreaStructureAttribute_numberOfLanes = @Value(uro_traffic_area_structure_attribute{0}.uro_traffic_area_structure_attribute_uro_number_of_lanes)
    -> AttributeManager_3
AttributeManager_3
    ATTR_TABLE:
      RENAME_SET_VALUE gml_id > tran_TrafficArea_gml_id
      RENAME_SET_VALUE gml_parent_id > tran_Road_gml_id
      RENAME_SET_VALUE citygml_creationDate > core_creationDate
      RENAME_SET_VALUE citygml_terminationDate > core_terminationDate
      RENAME_SET_VALUE citygml_surface_material > tran_surfaceMaterial
    USER_EXPOSED_ATTRIBUTES = OBJECTID,Shape_Length,Shape_Area
    -> TestFilter_TrafficArea
TestFilter_TrafficArea
    DEFAULT_VALUE = <UNFILTERED>
    TEST_LIST = "BOOL_OP,OR,COMPOSITE_TEST,""""""1"""""",TEST_CLAUSE,CASE_INSENSITIVE_TEST @Value(_geometory_lod) = 2",lod2_TrafficArea,"BOOL_OP,OR,COMPOSITE_TEST,""""""1"""""",TEST_CLAUSE,CASE_INSENSITIVE_TEST @Value(_geometory_lod) = 3",lod3_TrafficArea
    lod2_TrafficArea -> lod2_TrafficArea (writer GEODATABASE_FILE_1)
    lod3_TrafficArea -> lod3_TrafficArea (writer GEODATABASE_FILE_1)
lod2_TrafficArea (writer GEODATABASE_FILE_1)
    attributes: tran_TrafficArea_gml_id char(50), core_creationDate char(10), core_terminationDate char(10), tran_function char(10), tran_surfaceMaterial char(10), tran_Road_gml_id char(50)
lod3_TrafficArea (writer GEODATABASE_FILE_1)
    attributes: tran_TrafficArea_gml_id char(50), core_creationDate char(10), core_terminationDate char(10), tran_function char(10), tran_surfaceMaterial char(10), tran_Road_gml_id char(50)
Road (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, uro_road_data_quality_attribute{}.uro_road_data_quality_attribute_uro_src_scale{} xml_buffer, uro_road_data_quality_attribute{}.uro_road_data_quality_attribute_uro_src_scale{}.codeSpace xml_buffer, uro_road_data_quality_attribute{}.uro_road_data_quality_attribute_uro_geometry_src_desc{} xml_buffer, uro_road_data_quality_attribute{}.uro_road_data_quality_attribute_uro_geometry_src_desc{}.codeSpace xml_buffer, uro_road_data_quality_attribute{}.uro_road_data_quality_attribute_uro_thematic_src_desc{} xml_buffer, uro_road_data_quality_attribute{}.uro_road_data_quality_attribute_uro_thematic_src_desc{}.codeSpace xml_buffer, uro_road_data_quality_attribute{}.uro_road_data_quality_attribute_uro_appearance_src_desc{} xml_buffer,
      uro_road_data_quality_attribute{}.uro_road_data_quality_attribute_uro_appearance_src_desc{}.codeSpace xml_buffer, uro_road_data_quality_attribute{}.uro_road_data_quality_attribute_uro_lod_type xml_char(3), uro_road_structure_attribute{}.uro_road_structure_attribute_uro_width_type xml_buffer, uro_road_structure_attribute{}.uro_road_structure_attribute_uro_width_type_codeSpace xml_buffer, uro_road_structure_attribute{}.uro_road_structure_attribute_uro_width xml_real64, uro_road_structure_attribute{}.uro_road_structure_attribute_uro_width_units xml_buffer, uro_road_structure_attribute{}.uro_road_structure_attribute_uro_number_of_lanes xml_int64, uro_road_structure_attribute{}.uro_road_structure_attribute_uro_section_type xml_buffer, uro_road_structure_attribute{}.uro_road_structure_attribute_uro_section_type_codeSpace xml_buffer, uro_traffic_volume_attribute{}.uro_traffic_volume_attribute_uro_section_id xml_buffer, uro_traffic_volume_attribute{}.uro_traffic_volume_attribute_uro_weekday12hour_traffic_volume xml_int64, uro_traffic_volume_attribute{}.uro_traffic_volume_attribute_uro_weekday24hour_traffic_volume xml_int64, uro_traffic_volume_attribute{}.uro_traffic_volume_attribute_uro_large_vehicle_rate xml_real64, uro_traffic_volume_attribute{}.uro_traffic_volume_attribute_uro_congestion_rate xml_real64, uro_traffic_volume_attribute{}.uro_traffic_volume_attribute_uro_average_travel_speed_in_congestion xml_real64, uro_traffic_volume_attribute{}.uro_traffic_volume_attribute_uro_average_inbound_travel_speed_in_congestion xml_real64, uro_traffic_volume_attribute{}.uro_traffic_volume_attribute_uro_average_outbound_travel_speed_in_congestion xml_real64, uro_traffic_volume_attribute{}.uro_traffic_volume_attribute_uro_observation_point_name xml_buffer, uro_traffic_volume_attribute{}.uro_traffic_volume_attribute_uro_reference xml_buffer, uro_traffic_volume_attribute{}.uro_traffic_volume_attribute_uro_survey_year xml_buffer
    -> Deaggregator_4
Deaggregator_4
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> ListElementCounter_3
ListElementCounter_3
    CNT_ATTR = _lodCnt
    LIST_NAME = citygml_level_of_detail{}
    -> AttributeCreator
Note: リスト属性はインデックス「0」を指定して抽出
AttributeCreator
    ATTR_TABLE:
      SET_TO tran_function = @Value(citygml_function{0})
      SET_TO tran_usage = @Value(citygml_usage{0})
      SET_TO uro_RoadStructureAttribute_width = @Value(uro_road_structure_attribute{0}.uro_road_structure_attribute_uro_width)
      SET_TO uro_RoadStructureAttribute_widthType = @Value(uro_road_structure_attribute{0}.uro_road_structure_attribute_uro_width_type)
      SET_TO uro_trafficVolumeAttribute_weekday12hourTrafficVolume = @Value(uro_traffic_volume_attribute{0}.uro_traffic_volume_attribute_uro_weekday12hour_traffic_volume)
      SET_TO uro_trafficVolumeAttribute_weekday24hourTrafficVolume = @Value(uro_traffic_volume_attribute{0}.uro_traffic_volume_attribute_uro_weekday24hour_traffic_volume)
      SET_TO uro_trafficVolumeAttribute_largeVehicleRate = @Value(uro_traffic_volume_attribute{0}.uro_traffic_volume_attribute_uro_large_vehicle_rate)
      SET_TO uro_trafficVolumeAttribute_congestionRate = @Value(uro_traffic_volume_attribute{0}.uro_traffic_volume_attribute_uro_congestion_rate)
      SET_TO uro_trafficVolumeAttribute_averageTravelSpeedInCongestion = @Value(uro_traffic_volume_attribute{0}.uro_traffic_volume_attribute_uro_average_travel_speed_in_congestion)
      SET_TO uro_trafficVolumeAttribute_observationPointName = @Value(uro_traffic_volume_attribute{0}.uro_traffic_volume_attribute_uro_observation_point_name)
      SET_TO uro_trafficVolumeAttribute_reference = @Value(uro_traffic_volume_attribute{0}.uro_traffic_volume_attribute_uro_reference)
      SET_TO uro_trafficVolumeAttribute_surveyYear = @Value(uro_traffic_volume_attribute{0}.uro_traffic_volume_attribute_uro_survey_year)
      SET_TO uro_RoadStructureAttribute_numberOfLanes = @Value(uro_road_structure_attribute{0}.uro_road_structure_attribute_uro_number_of_lanes)
      SET_TO uro_RoadStructureAttribute_sectionType = @Value(uro_road_structure_attribute{0}.uro_road_structure_attribute_uro_section_type)
      SET_TO uro_trafficVolumeAttribute_sectionID = @Value(uro_traffic_volume_attribute{0}.uro_traffic_volume_attribute_uro_section_id)
      SET_TO uro_trafficVolumeAttribute_averageOutboundTravelSpeedInCongestio = @Value(uro_traffic_volume_attribute{0}.uro_traffic_volume_attribute_uro_average_outbound_travel_speed_in_congestion)
      SET_TO uro_roadDataQualityAttribute_srcScale = @Value(uro_road_data_quality_attribute{0}.uro_road_data_quality_attribute_uro_src_scale{0})
      SET_TO uro_roadDataQualityAttribute_geometrySrcDesc = @Value(uro_road_data_quality_attribute{0}.uro_road_data_quality_attribute_uro_geometry_src_desc{0})
      SET_TO uro_roadDataQualityAttribute_thematicSrcDesc = @Value(uro_road_data_quality_attribute{0}.uro_road_data_quality_attribute_uro_thematic_src_desc{0})
      SET_TO uro_roadDataQualityAttribute_appearanceSrcDesc = @Value(uro_road_data_quality_attribute{0}.uro_road_data_quality_attribute_uro_appearance_src_desc{0})
      SET_TO uro_roadDataQualityAttribute_lodType = @Value(uro_road_data_quality_attribute{0}.uro_road_data_quality_attribute_uro_lod_type)
      SET_TO uro_trafficVolumeAttribute_averageInboundTravelSpeedInCongestion = @Value(uro_traffic_volume_attribute{0}.uro_traffic_volume_attribute_uro_average_inbound_travel_speed_in_congestion)
      SET_TO _geometory_lod = FME_CONDITIONAL:DEFAULT_VALUE'@Value(citygml_level_of_detail{@sum(@Value(_lodCnt),-1)})'BOOL_OP;OR;COMPOSITE_TEST;1;TEST @Value(_part_number) < @sum(@Value(_lodCnt),-1)'@Value(citygml_level_of_detail{@Value(_part_number)})'FME_NUM_CONDITIONS2___
    -> AttributeManager
AttributeManager
    ATTR_TABLE:
      RENAME_SET_VALUE gml_id > tran_Road_gml_id
      REMOVE gml_parent_id
      REMOVE citygml_target_uri
      REMOVE citygml_feature_role
      REMOVE citygml_feature_role_attr_name
      REMOVE citygml_feature_role_attr_val
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_class
      REMOVE citygml_class_codeSpace
      REMOVE citygml_function{}
      REMOVE citygml_function{}.codeSpace
      REMOVE citygml_usage{}
      REMOVE citygml_usage{}.codeSpace
      REMOVE citygml_traffic_area{}.xlink_href
      REMOVE citygml_auxiliary_traffic_area{}.xlink_href
      REMOVE citygml_level_of_detail{}
      REMOVE uro_road_data_quality_attribute{}.uro_road_data_quality_attribute_uro_src_scale{}
      REMOVE uro_road_data_quality_attribute{}.uro_road_data_quality_attribute_uro_src_scale{}.codeSpace
      REMOVE uro_road_data_quality_attribute{}.uro_road_data_quality_attribute_uro_geometry_src_desc{}
      REMOVE uro_road_data_quality_attribute{}.uro_road_data_quality_attribute_uro_geometry_src_desc{}.codeSpace
      REMOVE uro_road_data_quality_attribute{}.uro_road_data_quality_attribute_uro_thematic_src_desc{}
      REMOVE uro_road_data_quality_attribute{}.uro_road_data_quality_attribute_uro_thematic_src_desc{}.codeSpace
      REMOVE uro_road_data_quality_attribute{}.uro_road_data_quality_attribute_uro_appearance_src_desc{}
      REMOVE uro_road_data_quality_attribute{}.uro_road_data_quality_attribute_uro_appearance_src_desc{}.codeSpace
      REMOVE uro_road_data_quality_attribute{}.uro_road_data_quality_attribute_uro_lod_type
      REMOVE uro_road_structure_attribute{}.uro_road_structure_attribute_uro_width_type
      REMOVE uro_road_structure_attribute{}.uro_road_structure_attribute_uro_width_type_codeSpace
      REMOVE uro_road_structure_attribute{}.uro_road_structure_attribute_uro_width
      REMOVE uro_road_structure_attribute{}.uro_road_structure_attribute_uro_width_units
      REMOVE uro_road_structure_attribute{}.uro_road_structure_attribute_uro_number_of_lanes
      REMOVE uro_road_structure_attribute{}.uro_road_structure_attribute_uro_section_type
      REMOVE uro_road_structure_attribute{}.uro_road_structure_attribute_uro_section_type_codeSpace
      REMOVE uro_traffic_volume_attribute{}.uro_traffic_volume_attribute_uro_section_id
      REMOVE uro_traffic_volume_attribute{}.uro_traffic_volume_attribute_uro_weekday12hour_traffic_volume
      REMOVE uro_traffic_volume_attribute{}.uro_traffic_volume_attribute_uro_weekday24hour_traffic_volume
      REMOVE uro_traffic_volume_attribute{}.uro_traffic_volume_attribute_uro_large_vehicle_rate
      REMOVE uro_traffic_volume_attribute{}.uro_traffic_volume_attribute_uro_congestion_rate
      REMOVE uro_traffic_volume_attribute{}.uro_traffic_volume_attribute_uro_average_travel_speed_in_congestion
      REMOVE uro_traffic_volume_attribute{}.uro_traffic_volume_attribute_uro_average_inbound_travel_speed_in_congestion
      REMOVE uro_traffic_volume_attribute{}.uro_traffic_volume_attribute_uro_average_outbound_travel_speed_in_congestion
      REMOVE uro_traffic_volume_attribute{}.uro_traffic_volume_attribute_uro_observation_point_name
      REMOVE uro_traffic_volume_attribute{}.uro_traffic_volume_attribute_uro_reference
      REMOVE uro_traffic_volume_attribute{}.uro_traffic_volume_attribute_uro_survey_year
    USER_EXPOSED_ATTRIBUTES = uro_surveyYear,Shape_Length,OBJECTID,core_creationDate,core_terminationDate,tran_class,Shape_Area
    -> FeatureJoiner [LEFT]
Sampler
    RATE = 1
    SAMPLE_MODE = No
    SAMPLE_TYPE_LONG = First N Features
    SAMPLED -> XMLTemplater [ROOT]
    SAMPLED -> XMLTemplater [SUB]
    NOT_SAMPLED -> XMLTemplater [SUB]
XMLTemplater
    OUTPUT_XML_HEADER = Yes
    RESULT_ATTRIBUTE = _result
    ROOT_QUERY_EXPR:
      <root>{
          fme:process-features("SUB")
      }</root>
    SUB_QUERY_EXPR:
      declare namespace gml="http://www.opengis.net/gml";
      declare namespace gen="http://www.opengis.net/citygml/generics/2.0";
      declare namespace tran="http://www.opengis.net/citygml/transportation/2.0";

      {
      let $doc := fme:get-xml-attribute("text_line_data")
      for $b in $doc//tran:Road
      return
      <Road gml_id="{data($b/@gml:id)}">{
          for $genStrAttr in $b/gen:stringAttribute
          where $b/gen:stringAttribute
              let $tempgenstrname := "gen_"||{data($genStrAttr/@name)}
              let $genstrname := fn:translate($tempgenstrname, "・（(- 「」、。－+＋）)", "____________")
              let $genstrtype := "TEXT"
              return
              <attr name="{$genstrname}" type="{$genstrtype}">{data($genStrAttr/gen:value)}</attr>
          }{
          for $genIntAttr in $b/gen:intAttribute
          where $b/gen:intAttribute
              let $tempgenintname := "gen_"||{data($genIntAttr/@name)}
              let $genintname := fn:translate($tempgenintname, "・（(- 「」、。－+＋）)", "____________")
              let $geninttype := "LONG"
              return
              <attr name="{$genintname}" type="{$geninttype}">{data($genIntAttr/gen:value)}</attr>
          }{
          for $genDoubleAttr in $b/gen:doubleAttribute
          where $b/gen:doubleAttribute
              let $tempgendoublename := "gen_"||{data($genDoubleAttr/@name)}
              let $gendoublename := fn:translate($tempgendoublename, "・（(- 「」、。－+＋）)", "____________")
              let $gendoubletype := "DOUBLE"
              return
              <attr name="{$gendoublename}" type="{$gendoubletype}">{data($genDoubleAttr/gen:value)}</attr>
          }{
          for $genDateAttr in $b/gen:dateAttribute
          where $b/gen:dateAttribute
              let $tempgendatename := "gen_"||{data($genDateAttr/@name)}
              let $gendatename := fn:translate($tempgendatename, "・（(- 「」、。－+＋）)", "____________")
              let $gendatetype := "TEXT"
              return
              <attr name="{$gendatename}" type="{$gendatetype}">{data($genDateAttr/gen:value)}</attr>
          }{
          for $genUriAttr in $b/gen:uriAttribute
          where $b/gen:uriAttribute
              let $tempgenuriname := "gen_"||{data($genUriAttr/@name)}
              let $genuriname := fn:translate($tempgenuriname, "・（(- 「」、。－+＋）)", "____________")
              let $genuritype := "TEXT"
              return
              <attr name="{$genuriname}" type="{$genuritype}">{data($genUriAttr/gen:value)}</attr>
          }{
          for $genMeasureAttr in $b/gen:measureAttribute
          where $b/gen:measureAttribute
              let $tempgenmeasurename := "gen_"||{data($genMeasureAttr/@name)}
              let $genmeasurename := fn:translate($tempgenmeasurename, "・（(- 「」、。－+＋）)", "____________")
              let $genmeasuretype := "DOUBLE"
              return
              <attr name="{$genmeasurename}" type="{$genmeasuretype}">{data($genMeasureAttr/gen:value)}</attr>
          }{
          for $attrSet in $b/gen:genericAttributeSet
          where $attrSet/gen:measureAttribute
              for $measureAttr in $attrSet/gen:measureAttribute
              let $mtempname := "gen_"||{data($attrSet/@name)}||"_"||{data($measureAttr/@name)}
              let $mname := fn:translate($mtempname, "・（(- 「」、。－+＋）)", "____________")
              let $mtype := "DOUBLE"
              return
              <attr name="{$mname}" type="{$mtype}">{data($measureAttr/gen:value)}</attr>
          }{
          for $attrSet in $b/gen:genericAttributeSet
          where $attrSet/gen:intAttribute
              for $intAttr in $attrSet/gen:intAttribute
              let $itempname := "gen_"||{data($attrSet/@name)}||"_"||{data($intAttr/@name)}
              let $iname := fn:translate($itempname, "・（(- 「」、。－+＋）)", "____________")
              let $itype := "LONG"
              return
              <attr name="{$iname}" type="{$itype}">{data($intAttr/gen:value)}</attr>
          }{
          for $attrSet in $b/gen:genericAttributeSet
          where $attrSet/gen:stringAttribute
              for $stringAttr in $attrSet/gen:stringAttribute
              let $stempname := "gen_"||{data($attrSet/@name)}||"_"||{data($stringAttr/@name)}
              let $sname := fn:translate($stempname, "・（(- 「」、。－+＋）)", "____________")
              let $stype := "TEXT"
              return
              <attr name="{$sname}" type="{$stype}">{data($stringAttr/gen:value)}</attr>
          }{
          for $attrSet in $b/gen:genericAttributeSet
          where $attrSet/gen:doubleAttribute
              for $doubleAttr in $attrSet/gen:doubleAttribute
              let $dtempname := "gen_"||{data($attrSet/@name)}||"_"||{data($doubleAttr/@name)}
              let $dname := fn:translate($dtempname, "・（(- 「」、。－+＋）)", "____________")
              let $dtype := "DOUBLE"
              return
              <attr name="{$dname}" type="{$dtype}">{data($doubleAttr/gen:value)}</attr>
          }{
          for $attrSet in $b/gen:genericAttributeSet
          where $attrSet/gen:dateAttribute
              for $dateAttr in $attrSet/gen:dateAttribute
              let $datetempname := "gen_"||{data($attrSet/@name)}||"_"||{data($dateAttr/@name)}
              let $datename := fn:translate($datetempname, "・（(- 「」、。－+＋）)", "____________")
              let $datetype := "TEXT"
              return
              <attr name="{$datename}" type="{$datetype}">{data($dateAttr/gen:value)}</attr>
          }{
          for $attrSet in $b/gen:genericAttributeSet
          where $attrSet/gen:uriAttribute
              for $uriAttr in $attrSet/gen:uriAttribute
              let $utempname := "gen_"||{data($attrSet/@name)}||"_"||{data($uriAttr/@name)}
              let $uname := fn:translate($utempname, "・（(- 「」、。－+＋）)", "____________")
              let $utype := "TEXT"
              return
              <attr name="{$uname}" type="{$utype}">{data($uriAttr/gen:value)}</attr>
          }</Road>
      }
    VISIBLE_QUERY_VALIDATE = Yes
    -> TextDecoder
TextDecoder
    DEST_ATTR = _decoded
    ENCODING_TYPE = XML
    STRING_TO_DECODE = @Value(_result)
    -> XMLFormatter
XMLFormatter
    COLLAPSE_EMPTY_ELEMENT = No
    FORMATTING_CHOICE = Pretty-Print XML
    INDENT_SIZE = 1
    LIST_NAME = _xml_error
    NAMESPACE_CLEANUP = No
    OUTPUT_ENCODING = utf-8
    REMOVE_ALL_COMMENT = No
    REMOVE_EMPTY_ELEMENT = No
    REMOVE_XML_HEADER = no
    REPLACE_TABS_WITH_SPACES = no
    SCHEMALOC_CLEANUP = No
    TEXT_INDENT = no
    WHITESPACE_HANDLING = Preserve all whitespace
    XML_ATTR_TEXT = _decoded
    XML_INPUT_TYPE = Attribute Specifying XML Text
    XML_OUTPUT_ATTR = _result
    XML_OUTPUT_TYPE = Attribute
    PASSED -> AttributeKeeper
AttributeKeeper
    CREATE_BULK_MODE_FEATURES = NO
    KEEP_ATTRS = _result
    -> XMLFragmenter
XMLFragmenter
    ATTRIBUTE_XML = _result
    EMBEDDED_EXPRESSIONS = root/Road
    FEATURE_TYPES_FORMAT_NAME = XML
    MERGE_ATTRS = No
    REJECT_FEATURES_WITH_NO_FRAGMENTS = YES
    XML_SOURCE_TYPE = Attribute with XML document
    FRAGMENTS -> XMLXQueryExtractor
XMLXQueryExtractor
    NEW_ATTRIBUTES = tran_id
    QUERY_EXPR:
      declare namespace gml="http://www.opengis.net/gml";
      declare namespace gen="http://www.opengis.net/citygml/generics/2.0";
      declare namespace tran="http://www.opengis.net/citygml/transportation/2.0";

      fme:set-attribute('tran_id', data(/Road/@gml_id))
    RESULT_ATTRIBUTE = _result
    RESULT_TYPE_NAME = Separated values
    SEPARATOR_VALUE = ,
    WRITE_XML_HEADER = No
    XML_ATTR = xml_fragment
    XML_REMOVE_SOURCE_ATTR = No
    XML_TYPE = Attribute specifying XML
    XQUERY_TYPE = XQuery expression
    QUERY_RESULTS -> AttributeManager_4
AttributeManager_4
    ATTR_TABLE:
      RENAME_SET_VALUE xml_fragment > xml_genericAttributeSet
      REMOVE xml_id
      REMOVE xml_matched_element
      REMOVE xml_parent_id
      REMOVE xml_parent_child_pos
      REMOVE _result
    USER_EXPOSED_ATTRIBUTES = building_id
    -> FeatureJoiner [RIGHT]
FeatureJoiner
    ATTR_CONFLICT_RES = Prefer Left
    GEOMETRY_HANDLING = Prefer Left
    JOIN_KEYS = tran_Road_gml_id tran_id AUTO
    JOIN_MODE = Inner
    JOINED -> TestFilter_Road
TestFilter_Road
    DEFAULT_VALUE = <UNFILTERED>
    TEST_LIST = "BOOL_OP,OR,COMPOSITE_TEST,""""""1"""""",TEST_CLAUSE,CASE_INSENSITIVE_TEST @Value(_geometory_lod) = 0",lod0_Road,"BOOL_OP,OR,COMPOSITE_TEST,""""""1"""""",TEST_CLAUSE,CASE_INSENSITIVE_TEST @Value(_geometory_lod) = 1",lod1_Road,"BOOL_OP,OR,COMPOSITE_TEST,""""""1"""""",TEST_CLAUSE,CASE_INSENSITIVE_TEST @Value(_geometory_lod) = 2",lod2_Road,"BOOL_OP,OR,COMPOSITE_TEST,""""""1"""""",TEST_CLAUSE,CASE_INSENSITIVE_TEST @Value(_geometory_lod) = 3",lod3_Road
    lod0_Road -> GeometryPartExtractor
    lod1_Road -> lod1_Road (writer GEODATABASE_FILE_1)
    lod2_Road -> lod2_Road (writer GEODATABASE_FILE_1)
    lod3_Road -> lod3_Road (writer GEODATABASE_FILE_1)
GeometryPartExtractor
    GQUERY:
      for $geom in //geometry
      where $geom/parent::geometry/@fme_geometry_type = 'IFMEFace'
      return number($geom/@fme_id)
    EXTRACTED -> lod0_Road (writer GEODATABASE_FILE_1)
lod0_Road (writer GEODATABASE_FILE_1)
    attributes: tran_Road_gml_id char(50), gml_description char(50), gml_name char(50), core_creationDate char(10), core_terminationDate char(10), tran_class char(10), tran_function char(10), tran_usage char(10), uro_RoadStructureAttribute_width double, uro_RoadStructureAttribute_widthType char(10), uro_RoadStructureAttribute_numberOfLanes integer, uro_RoadStructureAttribute_sectionType char(10), uro_trafficVolumeAttribute_sectionID char(11), uro_trafficVolumeAttribute_weekday12hourTrafficVolume integer, uro_trafficVolumeAttribute_weekday24hourTrafficVolume integer, uro_trafficVolumeAttribute_largeVehicleRate double, uro_trafficVolumeAttribute_congestionRate double, uro_trafficVolumeAttribute_averageTravelSpeedInCongestion double, uro_trafficVolumeAttribute_averageInboundTravelSpeedInCongestion double, uro_trafficVolumeAttribute_averageOutboundTravelSpeedInCongestio double, uro_trafficVolumeAttribute_observationPointName char(50), uro_trafficVolumeAttribute_reference char(10), uro_trafficVolumeAttribute_surveyYear char(10), uro_roadDataQualityAttribute_srcScale char(10), uro_roadDataQualityAttribute_geometrySrcDesc char(10), uro_roadDataQualityAttribute_thematicSrcDesc char(10), uro_roadDataQualityAttribute_appearanceSrcDesc char(10), uro_roadDataQualityAttribute_lodType char(10), xml_genericAttributeSet char(10000)
lod1_Road (writer GEODATABASE_FILE_1)
    attributes: tran_Road_gml_id char(50), gml_description char(50), gml_name char(50), core_creationDate char(10), core_terminationDate char(10), tran_class char(10), tran_function char(10), tran_usage char(10), uro_RoadStructureAttribute_width double, uro_RoadStructureAttribute_widthType char(10), uro_RoadStructureAttribute_numberOfLanes integer, uro_RoadStructureAttribute_sectionType char(10), uro_trafficVolumeAttribute_sectionID char(11), uro_trafficVolumeAttribute_weekday12hourTrafficVolume integer, uro_trafficVolumeAttribute_weekday24hourTrafficVolume integer, uro_trafficVolumeAttribute_largeVehicleRate double, uro_trafficVolumeAttribute_congestionRate double, uro_trafficVolumeAttribute_averageTravelSpeedInCongestion double, uro_trafficVolumeAttribute_averageInboundTravelSpeedInCongestion double, uro_trafficVolumeAttribute_averageOutboundTravelSpeedInCongestio double, uro_trafficVolumeAttribute_observationPointName char(50), uro_trafficVolumeAttribute_reference char(10), uro_trafficVolumeAttribute_surveyYear char(10), uro_roadDataQualityAttribute_srcScale char(10), uro_roadDataQualityAttribute_geometrySrcDesc char(10), uro_roadDataQualityAttribute_thematicSrcDesc char(10), uro_roadDataQualityAttribute_appearanceSrcDesc char(10), uro_roadDataQualityAttribute_lodType char(10), xml_genericAttributeSet char(10000)
lod2_Road (writer GEODATABASE_FILE_1)
    attributes: tran_Road_gml_id char(50), gml_description char(50), gml_name char(50), core_creationDate char(10), core_terminationDate char(10), tran_class char(10), tran_function char(10), tran_usage char(10), uro_RoadStructureAttribute_width double, uro_RoadStructureAttribute_widthType char(10), uro_RoadStructureAttribute_numberOfLanes integer, uro_RoadStructureAttribute_sectionType char(10), uro_trafficVolumeAttribute_sectionID char(11), uro_trafficVolumeAttribute_weekday12hourTrafficVolume integer, uro_trafficVolumeAttribute_weekday24hourTrafficVolume integer, uro_trafficVolumeAttribute_largeVehicleRate double, uro_trafficVolumeAttribute_congestionRate double, uro_trafficVolumeAttribute_averageTravelSpeedInCongestion double, uro_trafficVolumeAttribute_averageInboundTravelSpeedInCongestion double, uro_trafficVolumeAttribute_averageOutboundTravelSpeedInCongestio double, uro_trafficVolumeAttribute_observationPointName char(50), uro_trafficVolumeAttribute_reference char(10), uro_trafficVolumeAttribute_surveyYear char(10), uro_roadDataQualityAttribute_srcScale char(10), uro_roadDataQualityAttribute_geometrySrcDesc char(10), uro_roadDataQualityAttribute_thematicSrcDesc char(10), uro_roadDataQualityAttribute_appearanceSrcDesc char(10), uro_roadDataQualityAttribute_lodType char(10), xml_genericAttributeSet char(10000)
lod3_Road (writer GEODATABASE_FILE_1)
    attributes: tran_Road_gml_id char(50), gml_description char(50), gml_name char(50), core_creationDate char(10), core_terminationDate char(10), tran_class char(10), tran_function char(10), tran_usage char(10), uro_RoadStructureAttribute_width double, uro_RoadStructureAttribute_widthType char(10), uro_RoadStructureAttribute_numberOfLanes integer, uro_RoadStructureAttribute_sectionType char(10), uro_trafficVolumeAttribute_sectionID char(11), uro_trafficVolumeAttribute_weekday12hourTrafficVolume integer, uro_trafficVolumeAttribute_weekday24hourTrafficVolume integer, uro_trafficVolumeAttribute_largeVehicleRate double, uro_trafficVolumeAttribute_congestionRate double, uro_trafficVolumeAttribute_averageTravelSpeedInCongestion double, uro_trafficVolumeAttribute_averageInboundTravelSpeedInCongestion double, uro_trafficVolumeAttribute_averageOutboundTravelSpeedInCongestio double, uro_trafficVolumeAttribute_observationPointName char(50), uro_trafficVolumeAttribute_reference char(10), uro_trafficVolumeAttribute_surveyYear char(10), uro_roadDataQualityAttribute_srcScale char(10), uro_roadDataQualityAttribute_geometrySrcDesc char(10), uro_roadDataQualityAttribute_thematicSrcDesc char(10), uro_roadDataQualityAttribute_appearanceSrcDesc char(10), uro_roadDataQualityAttribute_lodType char(10), xml_genericAttributeSet char(10000)
lod1_Road (reader GEODATABASE_XML_1)
    attributes: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

Bookmark: Generic プロパティ
text_line (reader TEXTLINE_1)
    attributes: text_line_data buffer
    -> Sampler
