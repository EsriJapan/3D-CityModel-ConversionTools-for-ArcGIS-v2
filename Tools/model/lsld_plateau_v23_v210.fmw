FME workspace lsld_plateau_v23_v210.fmw

Parameters:
- SourceDataset_CITYGML =   # Input CityGML File(s)
- TEMPLATEFILE_GEODATABASE_FILE =   # Template XML Workspace Document (Schema Only)
- DestDataset_GEODATABASE_FILE =   # Output File Geodatabase

Readers:
- CITYGML_1: CITYGML from $(SourceDataset_CITYGML)
- GEODATABASE_XML_1: GEODATABASE_XML from $(TEMPLATEFILE_GEODATABASE_FILE)

Writers:
- GEODATABASE_FILE_2: GEODATABASE_FILE to $(DestDataset_GEODATABASE_FILE)

SedimentDisasterProneArea (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), urf_class xml_buffer, urf_class_codeSpace xml_buffer, urf_function{} xml_buffer, urf_function{}.codeSpace xml_buffer, urf_usage{} xml_buffer, urf_usage{}.codeSpace xml_buffer, urf_valid_from xml_date, urf_valid_from_type xml_buffer, urf_valid_from_type_codeSpace xml_buffer, urf_enactment_fiscal_year xml_buffer, urf_valid_to xml_date, urf_valid_to_type xml_buffer, urf_valid_to_type_codeSpace xml_buffer, urf_expiration_fiscal_year xml_buffer, urf_legal_grounds xml_buffer, urf_custodian xml_buffer,
      urf_notification_number xml_buffer, urf_urban_plan_type xml_buffer, urf_urban_plan_type_codeSpace xml_buffer, urf_area_classification_type xml_buffer, urf_area_classification_type_codeSpace xml_buffer, urf_nominal_area xml_real64, urf_nominal_area_units xml_buffer, urf_prefecture xml_buffer, urf_prefecture_codeSpace xml_buffer, urf_city xml_buffer, urf_city_codeSpace xml_buffer, urf_reference xml_buffer, urf_reason xml_buffer, urf_reason_xlink_href xml_buffer, urf_note xml_buffer, urf_note_xlink_href xml_buffer, urf_survey_year xml_buffer, citygml_level_of_detail{} xml_buffer, urf_target{}.xlink_href xml_buffer, urf_boundary{}.xlink_href xml_buffer, urf_location xml_buffer, urf_disaster_type xml_buffer, urf_disaster_type_codeSpace xml_buffer, urf_area_type xml_buffer, urf_area_type_codeSpace xml_buffer, urf_zone_number xml_buffer, urf_zone_name xml_buffer, urf_status xml_buffer, urf_status_codeSpace xml_buffer
    -> AttributeManager
AttributeManager
    ATTR_TABLE:
      RENAME_SET_VALUE gml_id > urf_SedimentDisasterProneArea_gml_id
      REMOVE gml_parent_id
      REMOVE citygml_target_uri
      REMOVE citygml_feature_role
      REMOVE citygml_feature_role_attr_name
      REMOVE citygml_feature_role_attr_val
      REMOVE gml_description
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_class
      REMOVE citygml_class_codeSpace
      REMOVE citygml_function{}
      REMOVE citygml_function{}.codeSpace
      REMOVE citygml_usage{}
      REMOVE citygml_usage{}.codeSpace
      REMOVE citygml_level_of_detail{}
      RENAME_SET_VALUE urf_valid_from > urf_validFrom
      RENAME_SET_VALUE urf_valid_from_type > urf_validFromType
      REMOVE urf_expiration_fiscal_year
      REMOVE urf_legal_grounds
      REMOVE urf_custodian
      REMOVE urf_notification_number
      REMOVE urf_urban_plan_type
      REMOVE urf_urban_plan_type_codeSpace
      REMOVE urf_area_classification_type
      REMOVE urf_area_classification_type_codeSpace
      REMOVE urf_nominal_area
      REMOVE urf_nominal_area_units
      RENAME_SET_VALUE urf_prefecture
      REMOVE urf_prefecture_codeSpace
      REMOVE urf_city
      REMOVE urf_city_codeSpace
      REMOVE urf_reference
      REMOVE urf_reason
      REMOVE urf_reason_xlink_href
      REMOVE urf_note
      REMOVE urf_note_xlink_href
      REMOVE urf_survey_year
      REMOVE urf_target{}.xlink_href
      REMOVE urf_boundary{}.xlink_href
      RENAME_SET_VALUE urf_disaster_type > urf_disasterType
      RENAME_SET_VALUE urf_area_type > urf_areaType
      RENAME_SET_VALUE urf_zone_number > urf_zoneNumber
      RENAME_SET_VALUE urf_zone_name > urf_zoneName
    -> AttributeEncoder
AttributeEncoder
    ATTRCHOICE = All Attributes
    DEST_ENCODING = utf-8
    TREAT_AS_BYTES = Honor Encoding
    -> GeometryPartExtractor
GeometryPartExtractor
    GQUERY:
      for $geom in //geometry
      where $geom/parent::geometry/@fme_geometry_type = 'IFMEFace'
      return number($geom/@fme_id)
    EXTRACTED -> lod1_SedimentDisasterProneArea (writer GEODATABASE_FILE_2)
lod1_SedimentDisasterProneArea (writer GEODATABASE_FILE_2)
    attributes: urf_SedimentDisasterProneArea_gml_id char(50), core_creationDate char(10), core_terminationDate char(10), urf_validFrom char(10), urf_validFromType char(10), urf_prefecture char(10), urf_location char(50), urf_disasterType char(10), urf_areaType char(10), urf_zoneNumber char(10), urf_zoneName char(50), urf_status char(10)
lod1_SedimentDisasterProneArea (reader GEODATABASE_XML_1)
    attributes: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
