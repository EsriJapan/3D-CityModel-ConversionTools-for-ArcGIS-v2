FME workspace dem_plateau_v23_v200.fmw

Parameters:
- SourceDataset_CITYGML =   # Input CityGML File(s)
- TEMPLATEFILE_GEODATABASE_FILE =   # Template XML Workspace Document (Schema Only)
- DestDataset_GEODATABASE_FILE =   # Output File Geodatabase

Readers:
- TEXTLINE_1: TEXTLINE from $(SourceDataset_CITYGML)
- CITYGML_1: CITYGML from $(SourceDataset_CITYGML)
- GEODATABASE_XML_1: GEODATABASE_XML from $(TEMPLATEFILE_GEODATABASE_FILE)

Writers:
- GEODATABASE_FILE_2: GEODATABASE_FILE to $(DestDataset_GEODATABASE_FILE)

CityModel (reader CITYGML_1)
    attributes: citygml_target_uri xml_buffer, gml_description xml_buffer, gml_name xml_buffer, citygml_city_object_member{}.xlink_href xml_buffer, gml_feature_member{}.xlink_href xml_buffer
ReliefFeature (reader CITYGML_1)
    attributes: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
TINRelief (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38)
    -> AttributeManager_TINRelief
AttributeManager_TINRelief
    ATTR_TABLE:
      RENAME_SET_VALUE gml_id > dem_TINRelief_gml_id
      REMOVE gml_parent_id
      REMOVE citygml_target_uri
      REMOVE citygml_feature_role
      REMOVE citygml_feature_role_attr_name
      REMOVE citygml_feature_role_attr_val
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      RENAME_SET_VALUE citygml_level_of_detail > dem_lod
    -> FeatureJoiner_2 [LEFT]
MassPointRelief (reader CITYGML_1) [off]
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38)
    -> AttributeManager_MassPointRelief
AttributeManager_MassPointRelief [off]
    ATTR_TABLE:
      RENAME_SET_VALUE gml_id > dem_MassPointRelief_gml_id
      REMOVE gml_parent_id
      REMOVE citygml_target_uri
      REMOVE citygml_feature_role
      REMOVE citygml_feature_role_attr_name
      REMOVE citygml_feature_role_attr_val
      RENAME_SET_VALUE citygml_creationDate > core_creationDate
      RENAME_SET_VALUE citygml_terminationDate > core_terminationDate
      REMOVE externalReference{}.externalObject.uri
      REMOVE externalReference{}.informationSystem
      REMOVE citygml_generalizes_to{}.xlink_href
      REMOVE citygml_relative_to_terrain
      REMOVE citygml_relative_to_water
      RENAME_SET_VALUE citygml_level_of_detail > dem_lod
    -> FeatureJoiner [LEFT]
Sampler
    RATE = 1
    SAMPLE_MODE = No
    SAMPLE_TYPE_LONG = First N Features
    SAMPLED -> XMLTemplater [ROOT]
    SAMPLED -> XMLTemplater [SUB]
    SAMPLED -> XMLTemplater_2 [ROOT] [off]
    SAMPLED -> XMLTemplater_2 [SUB] [off]
    NOT_SAMPLED -> XMLTemplater [SUB]
    NOT_SAMPLED -> XMLTemplater_2 [SUB] [off]
XMLTemplater
    OUTPUT_XML_HEADER = Yes
    RESULT_ATTRIBUTE = _result
    ROOT_QUERY_EXPR:
      <root>{
          fme:process-features("SUB")
      }</root>
    SUB_QUERY_EXPR:
      declare namespace gml="http://www.opengis.net/gml";
      declare namespace gen="http://www.opengis.net/citygml/generics/2.0";
      declare namespace dem="http://www.opengis.net/citygml/relief/2.0";

      {
      let $doc := fme:get-xml-attribute("text_line_data")
      for $b in $doc//dem:TINRelief
      return
      <TINRelief gml_id="{data($b/@gml:id)}">{
          for $genStrAttr in $b/gen:stringAttribute
          where $b/gen:stringAttribute
              let $tempgenstrname := "gen_"||{data($genStrAttr/@name)}
              let $genstrname := fn:translate($tempgenstrname, "・（(- 「」、。－+＋）)", "____________")
              let $genstrtype := "TEXT"
              return
              <attr name="{$genstrname}" type="{$genstrtype}">{data($genStrAttr/gen:value)}</attr>
          }{
          for $genIntAttr in $b/gen:intAttribute
          where $b/gen:intAttribute
              let $tempgenintname := "gen_"||{data($genIntAttr/@name)}
              let $genintname := fn:translate($tempgenintname, "・（(- 「」、。－+＋）)", "____________")
              let $geninttype := "LONG"
              return
              <attr name="{$genintname}" type="{$geninttype}">{data($genIntAttr/gen:value)}</attr>
          }{
          for $genDoubleAttr in $b/gen:doubleAttribute
          where $b/gen:doubleAttribute
              let $tempgendoublename := "gen_"||{data($genDoubleAttr/@name)}
              let $gendoublename := fn:translate($tempgendoublename, "・（(- 「」、。－+＋）)", "____________")
              let $gendoubletype := "DOUBLE"
              return
              <attr name="{$gendoublename}" type="{$gendoubletype}">{data($genDoubleAttr/gen:value)}</attr>
          }{
          for $genDateAttr in $b/gen:dateAttribute
          where $b/gen:dateAttribute
              let $tempgendatename := "gen_"||{data($genDateAttr/@name)}
              let $gendatename := fn:translate($tempgendatename, "・（(- 「」、。－+＋）)", "____________")
              let $gendatetype := "TEXT"
              return
              <attr name="{$gendatename}" type="{$gendatetype}">{data($genDateAttr/gen:value)}</attr>
          }{
          for $genUriAttr in $b/gen:uriAttribute
          where $b/gen:uriAttribute
              let $tempgenuriname := "gen_"||{data($genUriAttr/@name)}
              let $genuriname := fn:translate($tempgenuriname, "・（(- 「」、。－+＋）)", "____________")
              let $genuritype := "TEXT"
              return
              <attr name="{$genuriname}" type="{$genuritype}">{data($genUriAttr/gen:value)}</attr>
          }{
          for $genMeasureAttr in $b/gen:measureAttribute
          where $b/gen:measureAttribute
              let $tempgenmeasurename := "gen_"||{data($genMeasureAttr/@name)}
              let $genmeasurename := fn:translate($tempgenmeasurename, "・（(- 「」、。－+＋）)", "____________")
              let $genmeasuretype := "DOUBLE"
              return
              <attr name="{$genmeasurename}" type="{$genmeasuretype}">{data($genMeasureAttr/gen:value)}</attr>
          }{
          for $attrSet in $b/gen:genericAttributeSet
          where $attrSet/gen:measureAttribute
              for $measureAttr in $attrSet/gen:measureAttribute
              let $mtempname := "gen_"||{data($attrSet/@name)}||"_"||{data($measureAttr/@name)}
              let $mname := fn:translate($mtempname, "・（(- 「」、。－+＋）)", "____________")
              let $mtype := "DOUBLE"
              return
              <attr name="{$mname}" type="{$mtype}">{data($measureAttr/gen:value)}</attr>
          }{
          for $attrSet in $b/gen:genericAttributeSet
          where $attrSet/gen:intAttribute
              for $intAttr in $attrSet/gen:intAttribute
              let $itempname := "gen_"||{data($attrSet/@name)}||"_"||{data($intAttr/@name)}
              let $iname := fn:translate($itempname, "・（(- 「」、。－+＋）)", "____________")
              let $itype := "LONG"
              return
              <attr name="{$iname}" type="{$itype}">{data($intAttr/gen:value)}</attr>
          }{
          for $attrSet in $b/gen:genericAttributeSet
          where $attrSet/gen:stringAttribute
              for $stringAttr in $attrSet/gen:stringAttribute
              let $stempname := "gen_"||{data($attrSet/@name)}||"_"||{data($stringAttr/@name)}
              let $sname := fn:translate($stempname, "・（(- 「」、。－+＋）)", "____________")
              let $stype := "TEXT"
              return
              <attr name="{$sname}" type="{$stype}">{data($stringAttr/gen:value)}</attr>
          }{
          for $attrSet in $b/gen:genericAttributeSet
          where $attrSet/gen:doubleAttribute
              for $doubleAttr in $attrSet/gen:doubleAttribute
              let $dtempname := "gen_"||{data($attrSet/@name)}||"_"||{data($doubleAttr/@name)}
              let $dname := fn:translate($dtempname, "・（(- 「」、。－+＋）)", "____________")
              let $dtype := "DOUBLE"
              return
              <attr name="{$dname}" type="{$dtype}">{data($doubleAttr/gen:value)}</attr>
          }{
          for $attrSet in $b/gen:genericAttributeSet
          where $attrSet/gen:dateAttribute
              for $dateAttr in $attrSet/gen:dateAttribute
              let $datetempname := "gen_"||{data($attrSet/@name)}||"_"||{data($dateAttr/@name)}
              let $datename := fn:translate($datetempname, "・（(- 「」、。－+＋）)", "____________")
              let $datetype := "TEXT"
              return
              <attr name="{$datename}" type="{$datetype}">{data($dateAttr/gen:value)}</attr>
          }{
          for $attrSet in $b/gen:genericAttributeSet
          where $attrSet/gen:uriAttribute
              for $uriAttr in $attrSet/gen:uriAttribute
              let $utempname := "gen_"||{data($attrSet/@name)}||"_"||{data($uriAttr/@name)}
              let $uname := fn:translate($utempname, "・（(- 「」、。－+＋）)", "____________")
              let $utype := "TEXT"
              return
              <attr name="{$uname}" type="{$utype}">{data($uriAttr/gen:value)}</attr>
          }</TINRelief>
      }
    VISIBLE_QUERY_VALIDATE = Yes
    -> TextDecoder
XMLTemplater_2 [off]
    OUTPUT_XML_HEADER = Yes
    RESULT_ATTRIBUTE = _result
    ROOT_QUERY_EXPR:
      <root>{
          fme:process-features("SUB")
      }</root>
    SUB_QUERY_EXPR:
      declare namespace gml="http://www.opengis.net/gml";
      declare namespace gen="http://www.opengis.net/citygml/generics/2.0";
      declare namespace dem="http://www.opengis.net/citygml/relief/2.0";

      {
      let $doc := fme:get-xml-attribute("text_line_data")
      for $b in $doc//dem:MassPointRelief
      return
      <MassPointRelief gml_id="{data($b/@gml:id)}">{
          for $genStrAttr in $b/gen:stringAttribute
          where $b/gen:stringAttribute
              let $tempgenstrname := "gen_"||{data($genStrAttr/@name)}
              let $genstrname := fn:translate($tempgenstrname, "・（(- 「」、。－+＋）)", "____________")
              let $genstrtype := "TEXT"
              return
              <attr name="{$genstrname}" type="{$genstrtype}">{data($genStrAttr/gen:value)}</attr>
          }{
          for $genIntAttr in $b/gen:intAttribute
          where $b/gen:intAttribute
              let $tempgenintname := "gen_"||{data($genIntAttr/@name)}
              let $genintname := fn:translate($tempgenintname, "・（(- 「」、。－+＋）)", "____________")
              let $geninttype := "LONG"
              return
              <attr name="{$genintname}" type="{$geninttype}">{data($genIntAttr/gen:value)}</attr>
          }{
          for $genDoubleAttr in $b/gen:doubleAttribute
          where $b/gen:doubleAttribute
              let $tempgendoublename := "gen_"||{data($genDoubleAttr/@name)}
              let $gendoublename := fn:translate($tempgendoublename, "・（(- 「」、。－+＋）)", "____________")
              let $gendoubletype := "DOUBLE"
              return
              <attr name="{$gendoublename}" type="{$gendoubletype}">{data($genDoubleAttr/gen:value)}</attr>
          }{
          for $genDateAttr in $b/gen:dateAttribute
          where $b/gen:dateAttribute
              let $tempgendatename := "gen_"||{data($genDateAttr/@name)}
              let $gendatename := fn:translate($tempgendatename, "・（(- 「」、。－+＋）)", "____________")
              let $gendatetype := "TEXT"
              return
              <attr name="{$gendatename}" type="{$gendatetype}">{data($genDateAttr/gen:value)}</attr>
          }{
          for $genUriAttr in $b/gen:uriAttribute
          where $b/gen:uriAttribute
              let $tempgenuriname := "gen_"||{data($genUriAttr/@name)}
              let $genuriname := fn:translate($tempgenuriname, "・（(- 「」、。－+＋）)", "____________")
              let $genuritype := "TEXT"
              return
              <attr name="{$genuriname}" type="{$genuritype}">{data($genUriAttr/gen:value)}</attr>
          }{
          for $genMeasureAttr in $b/gen:measureAttribute
          where $b/gen:measureAttribute
              let $tempgenmeasurename := "gen_"||{data($genMeasureAttr/@name)}
              let $genmeasurename := fn:translate($tempgenmeasurename, "・（(- 「」、。－+＋）)", "____________")
              let $genmeasuretype := "DOUBLE"
              return
              <attr name="{$genmeasurename}" type="{$genmeasuretype}">{data($genMeasureAttr/gen:value)}</attr>
          }{
          for $attrSet in $b/gen:genericAttributeSet
          where $attrSet/gen:measureAttribute
              for $measureAttr in $attrSet/gen:measureAttribute
              let $mtempname := "gen_"||{data($attrSet/@name)}||"_"||{data($measureAttr/@name)}
              let $mname := fn:translate($mtempname, "・（(- 「」、。－+＋）)", "____________")
              let $mtype := "DOUBLE"
              return
              <attr name="{$mname}" type="{$mtype}">{data($measureAttr/gen:value)}</attr>
          }{
          for $attrSet in $b/gen:genericAttributeSet
          where $attrSet/gen:intAttribute
              for $intAttr in $attrSet/gen:intAttribute
              let $itempname := "gen_"||{data($attrSet/@name)}||"_"||{data($intAttr/@name)}
              let $iname := fn:translate($itempname, "・（(- 「」、。－+＋）)", "____________")
              let $itype := "LONG"
              return
              <attr name="{$iname}" type="{$itype}">{data($intAttr/gen:value)}</attr>
          }{
          for $attrSet in $b/gen:genericAttributeSet
          where $attrSet/gen:stringAttribute
              for $stringAttr in $attrSet/gen:stringAttribute
              let $stempname := "gen_"||{data($attrSet/@name)}||"_"||{data($stringAttr/@name)}
              let $sname := fn:translate($stempname, "・（(- 「」、。－+＋）)", "____________")
              let $stype := "TEXT"
              return
              <attr name="{$sname}" type="{$stype}">{data($stringAttr/gen:value)}</attr>
          }{
          for $attrSet in $b/gen:genericAttributeSet
          where $attrSet/gen:doubleAttribute
              for $doubleAttr in $attrSet/gen:doubleAttribute
              let $dtempname := "gen_"||{data($attrSet/@name)}||"_"||{data($doubleAttr/@name)}
              let $dname := fn:translate($dtempname, "・（(- 「」、。－+＋）)", "____________")
              let $dtype := "DOUBLE"
              return
              <attr name="{$dname}" type="{$dtype}">{data($doubleAttr/gen:value)}</attr>
          }{
          for $attrSet in $b/gen:genericAttributeSet
          where $attrSet/gen:dateAttribute
              for $dateAttr in $attrSet/gen:dateAttribute
              let $datetempname := "gen_"||{data($attrSet/@name)}||"_"||{data($dateAttr/@name)}
              let $datename := fn:translate($datetempname, "・（(- 「」、。－+＋）)", "____________")
              let $datetype := "TEXT"
              return
              <attr name="{$datename}" type="{$datetype}">{data($dateAttr/gen:value)}</attr>
          }{
          for $attrSet in $b/gen:genericAttributeSet
          where $attrSet/gen:uriAttribute
              for $uriAttr in $attrSet/gen:uriAttribute
              let $utempname := "gen_"||{data($attrSet/@name)}||"_"||{data($uriAttr/@name)}
              let $uname := fn:translate($utempname, "・（(- 「」、。－+＋）)", "____________")
              let $utype := "TEXT"
              return
              <attr name="{$uname}" type="{$utype}">{data($uriAttr/gen:value)}</attr>
          }</MassPointRelief>
      }
    VISIBLE_QUERY_VALIDATE = Yes
    -> TextDecoder
TextDecoder
    DEST_ATTR = _decoded
    ENCODING_TYPE = XML
    STRING_TO_DECODE = @Value(_result)
    -> XMLFormatter
XMLFormatter
    COLLAPSE_EMPTY_ELEMENT = No
    FORMATTING_CHOICE = Pretty-Print XML
    INDENT_SIZE = 1
    LIST_NAME = _xml_error
    NAMESPACE_CLEANUP = No
    OUTPUT_ENCODING = utf-8
    REMOVE_ALL_COMMENT = No
    REMOVE_EMPTY_ELEMENT = No
    REMOVE_XML_HEADER = no
    REPLACE_TABS_WITH_SPACES = no
    SCHEMALOC_CLEANUP = No
    TEXT_INDENT = no
    WHITESPACE_HANDLING = Preserve all whitespace
    XML_ATTR_TEXT = _decoded
    XML_INPUT_TYPE = Attribute Specifying XML Text
    XML_OUTPUT_ATTR = _result
    XML_OUTPUT_TYPE = Attribute
    PASSED -> AttributeKeeper
AttributeKeeper
    CREATE_BULK_MODE_FEATURES = NO
    KEEP_ATTRS = _result
    -> XMLFragmenter
    -> XMLFragmenter_2 [off]
XMLFragmenter
    ATTRIBUTE_XML = _result
    EMBEDDED_EXPRESSIONS = root/TINRelief
    FEATURE_TYPES_FORMAT_NAME = XML
    MERGE_ATTRS = No
    REJECT_FEATURES_WITH_NO_FRAGMENTS = YES
    XML_SOURCE_TYPE = Attribute with XML document
    FRAGMENTS -> XMLXQueryExtractor
XMLXQueryExtractor
    NEW_ATTRIBUTES = relief_id
    QUERY_EXPR:
      declare namespace gml="http://www.opengis.net/gml";
      declare namespace gen="http://www.opengis.net/citygml/generics/2.0";
      declare namespace dem="http://www.opengis.net/citygml/relief/2.0";

      fme:set-attribute('relief_id', data(/TINRelief/@gml_id))
    RESULT_ATTRIBUTE = _result
    RESULT_TYPE_NAME = Separated values
    SEPARATOR_VALUE = ,
    WRITE_XML_HEADER = No
    XML_ATTR = xml_fragment
    XML_REMOVE_SOURCE_ATTR = No
    XML_TYPE = Attribute specifying XML
    XQUERY_TYPE = XQuery expression
    QUERY_RESULTS -> AttributeManager
XMLFragmenter_2 [off]
    ATTRIBUTE_XML = _result
    EMBEDDED_EXPRESSIONS = MassPointRelief
    FEATURE_TYPES_FORMAT_NAME = XML
    MERGE_ATTRS = No
    REJECT_FEATURES_WITH_NO_FRAGMENTS = YES
    XML_SOURCE_TYPE = Attribute with XML document
    FRAGMENTS -> XMLXQueryExtractor_2 [off]
XMLXQueryExtractor_2 [off]
    NEW_ATTRIBUTES = relief_id
    QUERY_EXPR:
      declare namespace gml="http://www.opengis.net/gml";
      declare namespace gen="http://www.opengis.net/citygml/generics/2.0";
      declare namespace dem="http://www.opengis.net/citygml/relief/2.0";

      fme:set-attribute('relief_id', data(/MassPointRelief/@gml_id))
    RESULT_ATTRIBUTE = _result
    RESULT_TYPE_NAME = Separated values
    SEPARATOR_VALUE = ,
    WRITE_XML_HEADER = No
    XML_ATTR = xml_fragment
    XML_REMOVE_SOURCE_ATTR = No
    XML_TYPE = Attribute specifying XML
    XQUERY_TYPE = XQuery expression
    QUERY_RESULTS -> AttributeManager [off]
AttributeManager
    ATTR_TABLE:
      RENAME_SET_VALUE xml_fragment > xml_genericAttributeSet
      REMOVE xml_id
      REMOVE xml_matched_element
      REMOVE xml_parent_id
      REMOVE xml_parent_child_pos
      REMOVE _result
    USER_EXPOSED_ATTRIBUTES = building_id
    -> FeatureJoiner [RIGHT] [off]
    -> FeatureJoiner_2 [RIGHT]
FeatureJoiner_2
    ATTR_CONFLICT_RES = Prefer Left
    GEOMETRY_HANDLING = Prefer Left
    JOIN_KEYS = dem_TINRelief_gml_id relief_id AUTO
    JOIN_MODE = Inner
    JOINED -> TestFilter_TINRelief
TestFilter_TINRelief
    DEFAULT_VALUE = <UNFILTERED>
    PASSED_TEST_GROUP_OUTPUT = FIRST
    TEST_LIST = "BOOL_OP,OR,COMPOSITE_TEST,""""""1"""""",TEST_CLAUSE,TEST @Value(dem_lod) = 1",lod1,"BOOL_OP,OR,COMPOSITE_TEST,""""""1"""""",TEST_CLAUSE,TEST @Value(dem_lod) = 2",lod2,"BOOL_OP,OR,COMPOSITE_TEST,""""""1"""""",TEST_CLAUSE,TEST @Value(dem_lod) = 3",lod3
    lod1 -> lod1_TINRelief (writer GEODATABASE_FILE_2)
    lod2 -> lod2_TINRelief (writer GEODATABASE_FILE_2)
    lod3 -> lod3_TINRelief (writer GEODATABASE_FILE_2)
lod1_TINRelief (writer GEODATABASE_FILE_2)
    attributes: gml_description char(50), gml_name char(50), core_creationDate char(10), core_terminationDate char(10), dem_lod integer, xml_genericAttributeSet char(10000)
lod2_TINRelief (writer GEODATABASE_FILE_2)
    attributes: dem_TINRelief_gml_id char(50), gml_description char(50), gml_name char(50), core_creationDate char(10), core_terminationDate char(10), dem_lod integer, xml_genericAttributeSet char(10000)
lod3_TINRelief (writer GEODATABASE_FILE_2)
    attributes: dem_TINRelief_gml_id char(50), gml_description char(50), gml_name char(50), core_creationDate char(10), core_terminationDate char(10), dem_lod integer, xml_genericAttributeSet char(10000)
FeatureJoiner [off]
    ATTR_CONFLICT_RES = Prefer Left
    GEOMETRY_HANDLING = Prefer Left
    JOIN_KEYS = dem_MassPointRelief_gml_id relief_id AUTO
    JOIN_MODE = Inner
    JOINED -> TestFilter_MassPointRelief [off]
TestFilter_MassPointRelief [off]
    DEFAULT_VALUE = <UNFILTERED>
    PASSED_TEST_GROUP_OUTPUT = FIRST
    TEST_LIST = "BOOL_OP,OR,COMPOSITE_TEST,""""""1"""""",TEST_CLAUSE,TEST @Value(dem_lod) = 1",lod1,"BOOL_OP,OR,COMPOSITE_TEST,""""""1"""""",TEST_CLAUSE,TEST @Value(dem_lod) = 2",lod2,"BOOL_OP,OR,COMPOSITE_TEST,""""""1"""""",TEST_CLAUSE,TEST @Value(dem_lod) = 3",lod3
    lod1 -> lod1_MassPointRelief (writer GEODATABASE_FILE_2)
    lod2 -> lod2_MassPointRelief (writer GEODATABASE_FILE_2)
    lod3 -> lod3_MassPointRelief (writer GEODATABASE_FILE_2)
lod1_MassPointRelief (writer GEODATABASE_FILE_2) [off]
    attributes: dem_MassPointRelief_gml_id char(50), gml_description char(50), gml_name char(50), core_creationDate char(10), core_terminationDate char(10), dem_lod integer, xml_genericAttributeSet char(10000)
lod2_MassPointRelief (writer GEODATABASE_FILE_2) [off]
    attributes: dem_MassPointRelief_gml_id char(50), gml_description char(50), gml_name char(50), core_creationDate char(10), core_terminationDate char(10), dem_lod integer, xml_genericAttributeSet char(10000)
lod3_MassPointRelief (writer GEODATABASE_FILE_2) [off]
    attributes: dem_MassPointRelief_gml_id char(50), gml_description char(50), gml_name char(50), core_creationDate char(10), core_terminationDate char(10), dem_lod integer, xml_genericAttributeSet char(10000)
lod1_TINRelief (reader GEODATABASE_XML_1)
    attributes: OID integer, gml_description char(50), gml_name char(50), core_creationDate char(10), core_terminationDate char(10), dem_lod integer, xml_genericAttributeSet char(10000)

Bookmark: Generic プロパティ
text_line (reader TEXTLINE_1)
    attributes: text_line_data buffer
    -> Sampler
