FME workspace wtr_plateau_v23_v210.fmw

Parameters:
- SourceDataset_CITYGML =   # Input CityGML File(s)
- TEMPLATEFILE_GEODATABASE_FILE =   # Template XML Workspace Document (Schema Only)
- DestDataset_GEODATABASE_FILE =   # Output File Geodatabase

Readers:
- CITYGML_1: CITYGML from $(SourceDataset_CITYGML)
- TEXTLINE_1: TEXTLINE from $(SourceDataset_CITYGML)
- GEODATABASE_XML_1: GEODATABASE_XML from $(TEMPLATEFILE_GEODATABASE_FILE)

Writers:
- GEODATABASE_FILE_2: GEODATABASE_FILE to $(DestDataset_GEODATABASE_FILE)

WaterBody (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer, uro_flooding_risk_attribute{}.uro_water_body_high_tide_risk_attribute_uro_description xml_buffer, uro_flooding_risk_attribute{}.uro_water_body_high_tide_risk_attribute_uro_description_codeSpace xml_buffer, uro_flooding_risk_attribute{}.uro_water_body_high_tide_risk_attribute_uro_rank xml_buffer, uro_flooding_risk_attribute{}.uro_water_body_high_tide_risk_attribute_uro_rank_codeSpace xml_buffer, uro_flooding_risk_attribute{}.uro_water_body_high_tide_risk_attribute_uro_rank_org xml_buffer, uro_flooding_risk_attribute{}.uro_water_body_high_tide_risk_attribute_uro_rank_org_codeSpace xml_buffer, uro_flooding_risk_attribute{}.uro_water_body_high_tide_risk_attribute_uro_depth xml_real64, uro_flooding_risk_attribute{}.uro_water_body_high_tide_risk_attribute_uro_depth_units xml_buffer,
      uro_flooding_risk_attribute{}.uro_water_body_inland_flooding_risk_attribute_uro_description xml_buffer, uro_flooding_risk_attribute{}.uro_water_body_inland_flooding_risk_attribute_uro_description_codeSpace xml_buffer, uro_flooding_risk_attribute{}.uro_water_body_inland_flooding_risk_attribute_uro_rank xml_buffer, uro_flooding_risk_attribute{}.uro_water_body_inland_flooding_risk_attribute_uro_rank_codeSpace xml_buffer, uro_flooding_risk_attribute{}.uro_water_body_inland_flooding_risk_attribute_uro_rank_org xml_buffer, uro_flooding_risk_attribute{}.uro_water_body_inland_flooding_risk_attribute_uro_rank_org_codeSpace xml_buffer, uro_flooding_risk_attribute{}.uro_water_body_inland_flooding_risk_attribute_uro_depth xml_real64, uro_flooding_risk_attribute{}.uro_water_body_inland_flooding_risk_attribute_uro_depth_units xml_buffer, uro_flooding_risk_attribute{}.uro_water_body_river_flooding_risk_attribute_uro_description xml_buffer, uro_flooding_risk_attribute{}.uro_water_body_river_flooding_risk_attribute_uro_description_codeSpace xml_buffer, uro_flooding_risk_attribute{}.uro_water_body_river_flooding_risk_attribute_uro_rank xml_buffer, uro_flooding_risk_attribute{}.uro_water_body_river_flooding_risk_attribute_uro_rank_codeSpace xml_buffer, uro_flooding_risk_attribute{}.uro_water_body_river_flooding_risk_attribute_uro_rank_org xml_buffer, uro_flooding_risk_attribute{}.uro_water_body_river_flooding_risk_attribute_uro_rank_org_codeSpace xml_buffer, uro_flooding_risk_attribute{}.uro_water_body_river_flooding_risk_attribute_uro_depth xml_real64, uro_flooding_risk_attribute{}.uro_water_body_river_flooding_risk_attribute_uro_depth_units xml_buffer, uro_flooding_risk_attribute{}.uro_water_body_river_flooding_risk_attribute_uro_admin_type xml_buffer, uro_flooding_risk_attribute{}.uro_water_body_river_flooding_risk_attribute_uro_admin_type_codeSpace xml_buffer, uro_flooding_risk_attribute{}.uro_water_body_river_flooding_risk_attribute_uro_scale xml_buffer, uro_flooding_risk_attribute{}.uro_water_body_river_flooding_risk_attribute_uro_scale_codeSpace xml_buffer, uro_flooding_risk_attribute{}.uro_water_body_river_flooding_risk_attribute_uro_duration xml_real64, uro_flooding_risk_attribute{}.uro_water_body_river_flooding_risk_attribute_uro_duration_units xml_buffer, uro_flooding_risk_attribute{}.uro_water_body_tsunami_risk_attribute_uro_description xml_buffer, uro_flooding_risk_attribute{}.uro_water_body_tsunami_risk_attribute_uro_description_codeSpace xml_buffer, uro_flooding_risk_attribute{}.uro_water_body_tsunami_risk_attribute_uro_rank xml_buffer, uro_flooding_risk_attribute{}.uro_water_body_tsunami_risk_attribute_uro_rank_codeSpace xml_buffer, uro_flooding_risk_attribute{}.uro_water_body_tsunami_risk_attribute_uro_rank_org xml_buffer, uro_flooding_risk_attribute{}.uro_water_body_tsunami_risk_attribute_uro_rank_org_codeSpace xml_buffer, uro_flooding_risk_attribute{}.uro_water_body_tsunami_risk_attribute_uro_depth xml_real64, uro_flooding_risk_attribute{}.uro_water_body_tsunami_risk_attribute_uro_depth_units xml_buffer
    -> AttributeManager
AttributeManager
    ATTR_TABLE:
      RENAME_SET_VALUE gml_id > wtr_WaterBody_gml_id
      RENAME_SET_VALUE gml_parent_id > uro_WaterBodyRiverFloodingRiskAttribute_gml_id
      REMOVE gml_description
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      RENAME_SET_VALUE citygml_class > wtr_class
      REMOVE citygml_class_codeSpace
      SET_TO wtr_function = @Value(citygml_function{0})
      REMOVE citygml_function{}
      REMOVE citygml_function{}.codeSpace
      REMOVE citygml_usage{}
      REMOVE citygml_usage{}.codeSpace
      REMOVE citygml_level_of_detail{}
      REMOVE citygml_bounded_by{}.xlink_href
      SET_TO uro_WaterBodyHighTideRiskAttribute_description = @Value(uro_flooding_risk_attribute{0}.uro_water_body_high_tide_risk_attribute_uro_description)
      REMOVE uro_flooding_risk_attribute{}.uro_water_body_high_tide_risk_attribute_uro_description
      REMOVE uro_flooding_risk_attribute{}.uro_water_body_high_tide_risk_attribute_uro_description_codeSpace
      SET_TO uro_WaterBodyHighTideRiskAttribute_rank = @Value(uro_flooding_risk_attribute{0}.uro_water_body_high_tide_risk_attribute_uro_rank)
      REMOVE uro_flooding_risk_attribute{}.uro_water_body_high_tide_risk_attribute_uro_rank
      REMOVE uro_flooding_risk_attribute{}.uro_water_body_high_tide_risk_attribute_uro_rank_codeSpace
      SET_TO uro_WaterBodyHighTideRiskAttribute_rankOrg = @Value(uro_flooding_risk_attribute{0}.uro_water_body_high_tide_risk_attribute_uro_rank_org)
      REMOVE uro_flooding_risk_attribute{}.uro_water_body_high_tide_risk_attribute_uro_rank_org
      REMOVE uro_flooding_risk_attribute{}.uro_water_body_high_tide_risk_attribute_uro_rank_org_codeSpace
      REMOVE uro_flooding_risk_attribute{}.uro_water_body_high_tide_risk_attribute_uro_depth
      REMOVE uro_flooding_risk_attribute{}.uro_water_body_high_tide_risk_attribute_uro_depth_units
      SET_TO uro_WaterBodyInlandFloodingRiskAttribute_description = @Value(uro_flooding_risk_attribute{0}.uro_water_body_inland_flooding_risk_attribute_uro_description)
      REMOVE uro_flooding_risk_attribute{}.uro_water_body_inland_flooding_risk_attribute_uro_description
      REMOVE uro_flooding_risk_attribute{}.uro_water_body_inland_flooding_risk_attribute_uro_description_codeSpace
      SET_TO uro_WaterBodyInlandFloodingRiskAttribute_rank = @Value(uro_flooding_risk_attribute{0}.uro_water_body_inland_flooding_risk_attribute_uro_rank)
      REMOVE uro_flooding_risk_attribute{}.uro_water_body_inland_flooding_risk_attribute_uro_rank
      REMOVE uro_flooding_risk_attribute{}.uro_water_body_inland_flooding_risk_attribute_uro_rank_codeSpace
      SET_TO uro_WaterBodyInlandFloodingRiskAttribute_rankOrg = @Value(uro_flooding_risk_attribute{0}.uro_water_body_inland_flooding_risk_attribute_uro_rank_org)
      REMOVE uro_flooding_risk_attribute{}.uro_water_body_inland_flooding_risk_attribute_uro_rank_org
      REMOVE uro_flooding_risk_attribute{}.uro_water_body_inland_flooding_risk_attribute_uro_rank_org_codeSpace
      REMOVE uro_flooding_risk_attribute{}.uro_water_body_inland_flooding_risk_attribute_uro_depth
      REMOVE uro_flooding_risk_attribute{}.uro_water_body_inland_flooding_risk_attribute_uro_depth_units
      SET_TO uro_WaterBodyRiverFloodingRiskAttribute_description = @Value(uro_flooding_risk_attribute{0}.uro_water_body_river_flooding_risk_attribute_uro_description)
      REMOVE uro_flooding_risk_attribute{}.uro_water_body_river_flooding_risk_attribute_uro_description
      REMOVE uro_flooding_risk_attribute{}.uro_water_body_river_flooding_risk_attribute_uro_description_codeSpace
      SET_TO uro_WaterBodyRiverFloodingRiskAttribute_rank = @Value(uro_flooding_risk_attribute{0}.uro_water_body_river_flooding_risk_attribute_uro_rank)
      REMOVE uro_flooding_risk_attribute{}.uro_water_body_river_flooding_risk_attribute_uro_rank
      REMOVE uro_flooding_risk_attribute{}.uro_water_body_river_flooding_risk_attribute_uro_rank_codeSpace
      SET_TO uro_WaterBodyRiverFloodingRiskAttribute_rankOrg = @Value(uro_flooding_risk_attribute{0}.uro_water_body_river_flooding_risk_attribute_uro_rank_org)
      REMOVE uro_flooding_risk_attribute{}.uro_water_body_river_flooding_risk_attribute_uro_rank_org
      REMOVE uro_flooding_risk_attribute{}.uro_water_body_river_flooding_risk_attribute_uro_rank_org_codeSpace
      SET_TO uro_WaterBodyRiverFloodingRiskAttribute_depth = @Value(uro_flooding_risk_attribute{0}.uro_water_body_tsunami_risk_attribute_uro_depth)
      REMOVE uro_flooding_risk_attribute{}.uro_water_body_river_flooding_risk_attribute_uro_depth
      REMOVE uro_flooding_risk_attribute{}.uro_water_body_river_flooding_risk_attribute_uro_depth_units
      SET_TO uro_WaterBodyRiverFloodingRiskAttribute_adminType = @Value(uro_flooding_risk_attribute{0}.uro_water_body_river_flooding_risk_attribute_uro_admin_type)
      REMOVE uro_flooding_risk_attribute{}.uro_water_body_river_flooding_risk_attribute_uro_admin_type
      REMOVE uro_flooding_risk_attribute{}.uro_water_body_river_flooding_risk_attribute_uro_admin_type_codeSpace
      SET_TO uro_WaterBodyRiverFloodingRiskAttribute_scale = @Value(uro_flooding_risk_attribute{0}.uro_water_body_river_flooding_risk_attribute_uro_scale)
      REMOVE uro_flooding_risk_attribute{}.uro_water_body_river_flooding_risk_attribute_uro_scale
      REMOVE uro_flooding_risk_attribute{}.uro_water_body_river_flooding_risk_attribute_uro_scale_codeSpace
      SET_TO uro_WaterBodyRiverFloodingRiskAttribute_duration = @Value(uro_flooding_risk_attribute{0}.uro_water_body_river_flooding_risk_attribute_uro_duration)
      REMOVE uro_flooding_risk_attribute{}.uro_water_body_river_flooding_risk_attribute_uro_duration
      REMOVE uro_flooding_risk_attribute{}.uro_water_body_river_flooding_risk_attribute_uro_duration_units
      SET_TO uro_WaterBodyTsunamiRiskAttribute_description = @Value(uro_flooding_risk_attribute{0}.uro_water_body_tsunami_risk_attribute_uro_description)
      REMOVE uro_flooding_risk_attribute{}.uro_water_body_tsunami_risk_attribute_uro_description
      REMOVE uro_flooding_risk_attribute{}.uro_water_body_tsunami_risk_attribute_uro_description_codeSpace
      SET_TO uro_WaterBodyTsunamiRiskAttribute_rank = @Value(uro_flooding_risk_attribute{0}.uro_water_body_tsunami_risk_attribute_uro_rank)
      REMOVE uro_flooding_risk_attribute{}.uro_water_body_tsunami_risk_attribute_uro_rank
      REMOVE uro_flooding_risk_attribute{}.uro_water_body_tsunami_risk_attribute_uro_rank_codeSpace
      SET_TO uro_WaterBodyTsunamiRiskAttribute_rankOrg = @Value(uro_flooding_risk_attribute{0}.uro_water_body_tsunami_risk_attribute_uro_rank_org)
      REMOVE uro_flooding_risk_attribute{}.uro_water_body_tsunami_risk_attribute_uro_rank_org
      REMOVE uro_flooding_risk_attribute{}.uro_water_body_tsunami_risk_attribute_uro_rank_org_codeSpace
      REMOVE uro_flooding_risk_attribute{}.uro_water_body_tsunami_risk_attribute_uro_depth
      REMOVE uro_flooding_risk_attribute{}.uro_water_body_tsunami_risk_attribute_uro_depth_units
    -> FeatureJoiner [LEFT]
lod1_WaterBody (reader GEODATABASE_XML_1)
    attributes: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
Note: FeatureJoiner [FeatureJoiner] / Join Mode: / Join Mode: Left / Attribute Conflict Resolution: Use Left / Geometry Handling: Use Left / Join On: LeftRightComparison Modewtr_WaterBody_gml_idwaterbody_idAutomatic
FeatureJoiner
    ATTR_CONFLICT_RES = Use Left
    GEOMETRY_HANDLING = Use Left
    JOIN_KEYS = wtr_WaterBody_gml_id waterbody_id AUTO
    JOIN_MODE = Left
    JOINED -> AttributeEncoder
AttributeEncoder
    ATTRCHOICE = All Attributes
    DEST_ENCODING = utf-8
    TREAT_AS_BYTES = Honor Encoding
    -> FilenamePartExtractor
FilenamePartExtractor
    DIRNAME_ATTR = _dirname
    DIRPATH_ATTR = _dirpath
    EXTENSION_ATTR = _extension
    FULLNAME_ATTR = _filename
    ROOTNAME_ATTR = _rootname
    SRC_ATTR = $(TEMPLATEFILE_GEODATABASE_FILE)
    -> TestFilter
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(_filename) BEGINS_WITH fld",fld,"BOOL_OP,OR,COMPOSITE_TEST,""""""1"""""",TEST_CLAUSE,CASE_INSENSITIVE_TEST @Value(_filename) BEGINS_WITH tnm",tnm,"BOOL_OP,OR,COMPOSITE_TEST,""""""1"""""",TEST_CLAUSE,CASE_INSENSITIVE_TEST @Value(_filename) BEGINS_WITH htd",htd,"BOOL_OP,OR,COMPOSITE_TEST,""""""1"""""",TEST_CLAUSE,CASE_INSENSITIVE_TEST @Value(_filename) BEGINS_WITH ifld",ifld
    fld -> lod1_WaterBody_fld (writer GEODATABASE_FILE_2)
    tnm -> lod1_WaterBody_tnm (writer GEODATABASE_FILE_2)
    htd -> lod1_WaterBody_htd (writer GEODATABASE_FILE_2)
    ifld -> lod1_WaterBody_ifld (writer GEODATABASE_FILE_2)
lod1_WaterBody_fld (writer GEODATABASE_FILE_2)
    attributes: wtr_WaterBody_gml_id char(50), gml_name char(50), core_creationDate char(10), core_terminationDate char(10), wtr_class char(10), wtr_function char(10), uro_WaterBodyRiverFloodingRiskAttribute_gml_id char(50), uro_WaterBodyRiverFloodingRiskAttribute_description char(10), uro_WaterBodyRiverFloodingRiskAttribute_rank char(10), uro_WaterBodyRiverFloodingRiskAttribute_rankOrg char(10), uro_WaterBodyRiverFloodingRiskAttribute_adminType char(10), uro_WaterBodyRiverFloodingRiskAttribute_scale char(10), xml_genericAttributeSet char(10000)
lod1_WaterBody_tnm (writer GEODATABASE_FILE_2)
    attributes: wtr_WaterBody_gml_id char(50), gml_name char(50), core_creationDate char(10), core_terminationDate char(10), wtr_class char(10), wtr_function char(10), uro_WaterBodyRiverFloodingRiskAttribute_gml_id char(50), uro_WaterBodyTsunamiRiskAttribute_description char(10), uro_WaterBodyTsunamiRiskAttribute_rank char(10), uro_WaterBodyTsunamiRiskAttribute_rankOrg char(10), xml_genericAttributeSet char(10000)
lod1_WaterBody_htd (writer GEODATABASE_FILE_2)
    attributes: wtr_WaterBody_gml_id char(50), gml_name char(50), core_creationDate char(10), core_terminationDate char(10), wtr_class char(10), wtr_function char(10), uro_WaterBodyRiverFloodingRiskAttribute_gml_id char(50), uro_WaterBodyHighTideRiskAttribute_description char(10), uro_WaterBodyHighTideRiskAttribute_rank char(10), uro_WaterBodyHighTideRiskAttribute_rankOrg char(10), xml_genericAttributeSet char(10000)
lod1_WaterBody_ifld (writer GEODATABASE_FILE_2)
    attributes: wtr_WaterBody_gml_id char(50), gml_name char(50), core_creationDate char(10), core_terminationDate char(10), wtr_class char(10), wtr_function char(10), uro_WaterBodyRiverFloodingRiskAttribute_gml_id char(50), uro_WaterBodyInlandFloodingRiskAttribute_description char(10), uro_WaterBodyInlandFloodingRiskAttribute_rank char(10), uro_WaterBodyInlandFloodingRiskAttribute_rankOrg char(10), xml_genericAttributeSet char(10000)

Bookmark: 汎用属性セットの XMLフィールド を作成(xml_genericAttributeSet)
text_line (reader TEXTLINE_1)
    attributes: text_line_data buffer
    -> Sampler
Sampler
    RATE = 1
    SAMPLE_MODE = No
    SAMPLE_TYPE_LONG = First N Features
    SAMPLED -> XMLTemplater [ROOT]
    SAMPLED -> XMLTemplater [SUB]
    NOT_SAMPLED -> XMLTemplater [SUB]
Note: XMLTemplaterで作成するXML / ---------- / <?xml version="1.0" encoding="UTF-16"?> / <root> / <WaterBody gml_id="fld_0f4c7245-c2cd-4a2b-aba1-e9e71c2f286c"> / <attr name="gen_種類" type="TEXT">1</attr> / <attr name="gen_洪水浸水想定区域_計画規模__継続時間" type="DOUBLE">1.5</attr> / <attr name="gen_洪水浸水想定区域_計画規模__浸水深" type="DOUBLE">1.5</attr> / <attr name="gen_洪水浸水想定区域_計画規模__規模" type="TEXT">L1</attr> / <attr name="gen_洪水浸水想定区域_計画規模__浸水ランク" type="TEXT">1</attr> / </WaterBody> / (中略) / </root>
XMLTemplater
    OUTPUT_XML_HEADER = Yes
    RESULT_ATTRIBUTE = _result
    ROOT_QUERY_EXPR:
      <root>{
          fme:process-features("SUB")
      }</root>
    SUB_QUERY_EXPR:
      declare namespace gml="http://www.opengis.net/gml";
      declare namespace gen="http://www.opengis.net/citygml/generics/2.0";
      declare namespace wtr="http://www.opengis.net/citygml/waterbody/2.0";

      {
      let $doc := fme:get-xml-attribute("text_line_data")
      for $w in $doc//wtr:WaterBody
      return
      <WaterBody gml_id="{data($w/@gml:id)}">{
          for $genStrAttr in $w/gen:stringAttribute
          where $w/gen:stringAttribute
              let $tempgenstrname := "gen_"||{data($genStrAttr/@name)}
              let $genstrname := fn:translate($tempgenstrname, "・（(- 「」、。－+＋）)", "____________")
              let $genstrtype := "TEXT"
              return
              <attr name="{$genstrname}" type="{$genstrtype}">{data($genStrAttr/gen:value)}</attr>
          }{
          for $genIntAttr in $w/gen:intAttribute
          where $w/gen:intAttribute
              let $tempgenintname := "gen_"||{data($genIntAttr/@name)}
              let $genintname := fn:translate($tempgenintname, "・（(- 「」、。－+＋）)", "____________")
              let $geninttype := "LONG"
              return
              <attr name="{$genintname}" type="{$geninttype}">{data($genIntAttr/gen:value)}</attr>
          }{
          for $genDoubleAttr in $w/gen:doubleAttribute
          where $w/gen:doubleAttribute
              let $tempgendoublename := "gen_"||{data($genDoubleAttr/@name)}
              let $gendoublename := fn:translate($tempgendoublename, "・（(- 「」、。－+＋）)", "____________")
              let $gendoubletype := "DOUBLE"
              return
              <attr name="{$gendoublename}" type="{$gendoubletype}">{data($genDoubleAttr/gen:value)}</attr>
          }{
          for $genDateAttr in $w/gen:dateAttribute
          where $w/gen:dateAttribute
              let $tempgendatename := "gen_"||{data($genDateAttr/@name)}
              let $gendatename := fn:translate($tempgendatename, "・（(- 「」、。－+＋）)", "____________")
              let $gendatetype := "TEXT"
              return
              <attr name="{$gendatename}" type="{$gendatetype}">{data($genDateAttr/gen:value)}</attr>
          }{
          for $genUriAttr in $w/gen:uriAttribute
          where $w/gen:uriAttribute
              let $tempgenuriname := "gen_"||{data($genUriAttr/@name)}
              let $genuriname := fn:translate($tempgenuriname, "・（(- 「」、。－+＋）)", "____________")
              let $genuritype := "TEXT"
              return
              <attr name="{$genuriname}" type="{$genuritype}">{data($genUriAttr/gen:value)}</attr>
          }{
          for $genMeasureAttr in $w/gen:measureAttribute
          where $w/gen:measureAttribute
              let $tempgenmeasurename := "gen_"||{data($genMeasureAttr/@name)}
              let $genmeasurename := fn:translate($tempgenmeasurename, "・（(- 「」、。－+＋）)", "____________")
              let $genmeasuretype := "DOUBLE"
              return
              <attr name="{$genmeasurename}" type="{$genmeasuretype}">{data($genMeasureAttr/gen:value)}</attr>
          }{
          for $attrSet in $w/gen:genericAttributeSet
          where $attrSet/gen:measureAttribute
              for $measureAttr in $attrSet/gen:measureAttribute
              let $mtempname := "gen_"||{data($attrSet/@name)}||"_"||{data($measureAttr/@name)}
              let $mname := fn:translate($mtempname, "・（(- 「」、。－+＋）)", "____________")
              let $mtype := "DOUBLE"
              return
              <attr name="{$mname}" type="{$mtype}">{data($measureAttr/gen:value)}</attr>
          }{
          for $attrSet in $w/gen:genericAttributeSet
          where $attrSet/gen:intAttribute
              for $intAttr in $attrSet/gen:intAttribute
              let $itempname := "gen_"||{data($attrSet/@name)}||"_"||{data($intAttr/@name)}
              let $iname := fn:translate($itempname, "・（(- 「」、。－+＋）)", "____________")
              let $itype := "LONG"
              return
              <attr name="{$iname}" type="{$itype}">{data($intAttr/gen:value)}</attr>
          }{
          for $attrSet in $w/gen:genericAttributeSet
          where $attrSet/gen:stringAttribute
              for $stringAttr in $attrSet/gen:stringAttribute
              let $stempname := "gen_"||{data($attrSet/@name)}||"_"||{data($stringAttr/@name)}
              let $sname := fn:translate($stempname, "・（(- 「」、。－+＋）)", "____________")
              let $stype := "TEXT"
              return
              <attr name="{$sname}" type="{$stype}">{data($stringAttr/gen:value)}</attr>
          }{
          for $attrSet in $w/gen:genericAttributeSet
          where $attrSet/gen:doubleAttribute
              for $doubleAttr in $attrSet/gen:doubleAttribute
              let $dtempname := "gen_"||{data($attrSet/@name)}||"_"||{data($doubleAttr/@name)}
              let $dname := fn:translate($dtempname, "・（(- 「」、。－+＋）)", "____________")
              let $dtype := "DOUBLE"
              return
              <attr name="{$dname}" type="{$dtype}">{data($doubleAttr/gen:value)}</attr>
          }{
          for $attrSet in $w/gen:genericAttributeSet
          where $attrSet/gen:dateAttribute
              for $dateAttr in $attrSet/gen:dateAttribute
              let $datetempname := "gen_"||{data($attrSet/@name)}||"_"||{data($dateAttr/@name)}
              let $datename := fn:translate($datetempname, "・（(- 「」、。－+＋）)", "____________")
              let $datetype := "TEXT"
              return
              <attr name="{$datename}" type="{$datetype}">{data($dateAttr/gen:value)}</attr>
          }{
          for $attrSet in $w/gen:genericAttributeSet
          where $attrSet/gen:uriAttribute
              for $uriAttr in $attrSet/gen:uriAttribute
              let $utempname := "gen_"||{data($attrSet/@name)}||"_"||{data($uriAttr/@name)}
              let $uname := fn:translate($utempname, "・（(- 「」、。－+＋）)", "____________")
              let $utype := "TEXT"
              return
              <attr name="{$uname}" type="{$utype}">{data($uriAttr/gen:value)}</attr>
          }</WaterBody>
      }
    VISIBLE_QUERY_VALIDATE = Yes
    -> TextDecoder
TextDecoder
    DEST_ATTR = _decoded
    ENCODING_TYPE = XML
    STRING_TO_DECODE = @Value(_result)
    -> XMLFormatter
XMLFormatter
    COLLAPSE_EMPTY_ELEMENT = No
    FORMATTING_CHOICE = Pretty-Print XML
    INDENT_SIZE = 1
    LIST_NAME = _xml_error
    NAMESPACE_CLEANUP = Yes
    OUTPUT_ENCODING = utf-8
    REMOVE_ALL_COMMENT = No
    REMOVE_EMPTY_ELEMENT = No
    REMOVE_XML_HEADER = no
    REPLACE_TABS_WITH_SPACES = no
    SCHEMALOC_CLEANUP = No
    TEXT_INDENT = no
    WHITESPACE_HANDLING = Preserve all whitespace
    XML_ATTR_TEXT = _decoded
    XML_INPUT_TYPE = Attribute Specifying XML Text
    XML_OUTPUT_ATTR = _result
    XML_OUTPUT_TYPE = Attribute
    PASSED -> AttributeKeeper
AttributeKeeper
    CREATE_BULK_MODE_FEATURES = No
    KEEP_ATTRS = _result
    -> XMLFragmenter
Note: 図形ごとに、汎用属性のXMLを作成
XMLFragmenter
    ATTRIBUTE_XML = _result
    EMBEDDED_EXPRESSIONS = root/WaterBody
    FEATURE_TYPES_FORMAT_NAME = XML
    MERGE_ATTRS = No
    REJECT_FEATURES_WITH_NO_FRAGMENTS = YES
    XML_SOURCE_TYPE = Attribute with XML document
    FRAGMENTS -> XMLXQueryExtractor
Note: Joinするときにキーとして使用するgml_idを属性として格納
XMLXQueryExtractor
    NEW_ATTRIBUTES = waterbody_id
    QUERY_EXPR:
      declare namespace gml="http://www.opengis.net/gml";
      declare namespace gen="http://www.opengis.net/citygml/generics/2.0";
      declare namespace wtr="http://www.opengis.net/citygml/waterbody/2.0";

      fme:set-attribute('waterbody_id', data(/WaterBody/@gml_id))
    RESULT_ATTRIBUTE = _result
    RESULT_TYPE_NAME = Separated values
    SEPARATOR_VALUE = ,
    WRITE_XML_HEADER = No
    XML_ATTR = xml_fragment
    XML_REMOVE_SOURCE_ATTR = No
    XML_TYPE = Attribute specifying XML
    XQUERY_TYPE = XQuery expression
    QUERY_RESULTS -> AttributeManager_2
AttributeManager_2
    ATTR_TABLE:
      RENAME_SET_VALUE xml_fragment > xml_genericAttributeSet
      REMOVE xml_id
      REMOVE xml_matched_element
      REMOVE xml_parent_id
      REMOVE xml_parent_child_pos
      REMOVE _result
    -> FeatureJoiner [RIGHT]
