FME workspace bldg_plateau_v23_v200.fmw

Parameters:
- SourceDataset_CITYGML =   # Input CityGML File(s)
- TEMPLATEFILE_GEODATABASE_FILE =   # Template XML Workspace Document (Schema Only)
- DestDataset_GEODATABASE_FILE =   # Output File Geodatabase

Readers:
- TEXTLINE_1: TEXTLINE from $(SourceDataset_CITYGML)
- CITYGML_1: CITYGML from $(SourceDataset_CITYGML)
- GEODATABASE_XML_1: GEODATABASE_XML from $(TEMPLATEFILE_GEODATABASE_FILE)

Writers:
- GEODATABASE_FILE_1: GEODATABASE_FILE to $(DestDataset_GEODATABASE_FILE)

Deaggregator_CloserSurface
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> ListElementCounter_CloserSurface
ListElementCounter_CloserSurface
    CNT_ATTR = _lodCnt
    LIST_NAME = citygml_level_of_detail{}
    -> AttributeCreator_CloserSurface
AttributeCreator_CloserSurface
    ATTR_TABLE = SET_TO _geometory_lod = FME_CONDITIONAL:DEFAULT_VALUE'@Value(citygml_level_of_detail{@sum(@Value(_lodCnt),-1)})'BOOL_OP;OR;COMPOSITE_TEST;1;TEST @Value(_part_number) < @sum(@Value(_lodCnt),-1)'@Value(citygml_level_of_detail{@Value(_part_number)})'FME_NUM_CONDITIONS2___
    -> AttributeManager_CloserSurface
AttributeManager_CloserSurface
    ATTR_TABLE:
      RENAME_SET_VALUE gml_id > bldg_ClosureSurface_gml_id
      RENAME_SET_VALUE gml_parent_id > bldg_Building_gml_id
      REMOVE citygml_target_uri
      REMOVE citygml_feature_role
      REMOVE citygml_feature_role_attr_name
      REMOVE citygml_feature_role_attr_val
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE citygml_opening{}.xlink_href
    -> TestFilter_CloserSurface
TestFilter_CloserSurface
    DEFAULT_VALUE = <UNFILTERED>
    PASSED_TEST_GROUP_OUTPUT = FIRST
    TEST_LIST = "BOOL_OP,OR,COMPOSITE_TEST,""""""1"""""",TEST_CLAUSE,CASE_INSENSITIVE_TEST @Value(_geometry_name) = 2",lod2_CloserSurface,"BOOL_OP,OR,COMPOSITE_TEST,""""""1"""""",TEST_CLAUSE,CASE_INSENSITIVE_TEST @Value(_geometory_lod) = 3",lod3_CloserSurface
    lod2_CloserSurface -> lod2_ClosureSurface (writer GEODATABASE_FILE_1)
    lod3_CloserSurface -> lod3_ClosureSurface (writer GEODATABASE_FILE_1)
Deaggregator_BuildingInstallation
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> ListElementCounter_BuildingInstallation
ListElementCounter_BuildingInstallation
    CNT_ATTR = _lodCnt
    LIST_NAME = citygml_level_of_detail{}
    -> AttributeCreator_BuildingInstllation
AttributeCreator_BuildingInstllation
    ATTR_TABLE:
      SET_TO bldg_function = @Value(citygml_function{0})
      SET_TO _geometory_lod = FME_CONDITIONAL:DEFAULT_VALUE'@Value(citygml_level_of_detail{@sum(@Value(_lodCnt),-1)})'BOOL_OP;OR;COMPOSITE_TEST;1;TEST @Value(_part_number) < @sum(@Value(_lodCnt),-1)'@Value(citygml_level_of_detail{@Value(_part_number)})'FME_NUM_CONDITIONS2___
    -> AttributeManager_BuildingInstllation
AttributeManager_BuildingInstllation
    ATTR_TABLE:
      RENAME_SET_VALUE gml_id > bldg_BuildingInstallation_gml_id
      RENAME_SET_VALUE gml_parent_id > bldg_Building_gml_id
      REMOVE citygml_target_uri
      REMOVE citygml_feature_role
      REMOVE citygml_feature_role_attr_name
      REMOVE citygml_feature_role_attr_val
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      RENAME_SET_VALUE citygml_class > bldg_class
      REMOVE citygml_class_codeSpace
      REMOVE citygml_function{}
      REMOVE citygml_function{}.codeSpace
      REMOVE citygml_usage{}
      REMOVE citygml_usage{}.codeSpace
      REMOVE citygml_level_of_detail{}
      REMOVE citygml_bounded_by{}.xlink_href
    -> TestFilter_BuildingInstllation
TestFilter_BuildingInstllation
    DEFAULT_VALUE = <UNFILTERED>
    PASSED_TEST_GROUP_OUTPUT = FIRST
    TEST_LIST = "BOOL_OP,OR,COMPOSITE_TEST,""""""1"""""",TEST_CLAUSE,CASE_INSENSITIVE_TEST @Value(_geometory_lod) BEGINS_WITH 2",lod2_BuildingInstallation,"BOOL_OP,OR,COMPOSITE_TEST,""""""1"""""",TEST_CLAUSE,CASE_INSENSITIVE_TEST @Value(_geometory_lod) = 3",lod3_BuildingInstallation
    lod2_BuildingInstallation -> lod2_BuildingInstallation (writer GEODATABASE_FILE_1)
    lod3_BuildingInstallation -> lod3_BuildingInstallation (writer GEODATABASE_FILE_1)
AttributeManager_Window
    ATTR_TABLE:
      RENAME_SET_VALUE gml_id > bldg_Window_gml_id
      RENAME_SET_VALUE gml_parent_id > bldg_Building_gml_id
      REMOVE citygml_target_uri
      REMOVE citygml_feature_role
      REMOVE citygml_feature_role_attr_name
      REMOVE citygml_feature_role_attr_val
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_level_of_detail{}
    -> lod3_Window (writer GEODATABASE_FILE_1)
Deaggregator_WallSurface
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> ListElementCounter_WallSurface
ListElementCounter_WallSurface
    CNT_ATTR = _lodCnt
    LIST_NAME = citygml_level_of_detail{}
    -> AttributeCreator_WallSurface
AttributeCreator_WallSurface
    ATTR_TABLE = SET_TO _geometory_lod = FME_CONDITIONAL:DEFAULT_VALUE'@Value(citygml_level_of_detail{@sum(@Value(_lodCnt),-1)})'BOOL_OP;OR;COMPOSITE_TEST;1;TEST @Value(_part_number) < @sum(@Value(_lodCnt),-1)'@Value(citygml_level_of_detail{@Value(_part_number)})'FME_NUM_CONDITIONS2___
    -> AttributeManager_WallSurface
AttributeManager_WallSurface
    ATTR_TABLE:
      RENAME_SET_VALUE gml_id > bldg_WallSurface_gml_id
      RENAME_SET_VALUE gml_parent_id > bldg_Building_gml_id
      REMOVE citygml_target_uri
      REMOVE citygml_feature_role
      REMOVE citygml_feature_role_attr_name
      REMOVE citygml_feature_role_attr_val
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE citygml_opening{}.xlink_href
    -> TestFilter_WallSurface
TestFilter_WallSurface
    DEFAULT_VALUE = <UNFILTERED>
    PASSED_TEST_GROUP_OUTPUT = FIRST
    TEST_LIST = "BOOL_OP,OR,COMPOSITE_TEST,""""""1"""""",TEST_CLAUSE,CASE_INSENSITIVE_TEST @Value(_geometory_lod) = 2",lod2_WallSurface,"BOOL_OP,OR,COMPOSITE_TEST,""""""1"""""",TEST_CLAUSE,CASE_INSENSITIVE_TEST @Value(_geometory_lod) = 3",lod3_WallSurface
    lod2_WallSurface -> lod2_WallSurface (writer GEODATABASE_FILE_1)
    lod3_WallSurface -> lod3_WallSurface (writer GEODATABASE_FILE_1)
Deaggregator_RoofSurface
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> ListElementCounter_RoofSurface
ListElementCounter_RoofSurface
    CNT_ATTR = _lodCnt
    LIST_NAME = citygml_level_of_detail{}
    -> AttributeCreator_RoofSurface
AttributeCreator_RoofSurface
    ATTR_TABLE = SET_TO _geometory_lod = FME_CONDITIONAL:DEFAULT_VALUE'@Value(citygml_level_of_detail{@sum(@Value(_lodCnt),-1)})'BOOL_OP;OR;COMPOSITE_TEST;1;TEST @Value(_part_number) < @sum(@Value(_lodCnt),-1)'@Value(citygml_level_of_detail{@Value(_part_number)})'FME_NUM_CONDITIONS2___
    -> AttributeManager_RoofSurface
AttributeManager_RoofSurface
    ATTR_TABLE:
      RENAME_SET_VALUE gml_id > bldg_RoofSurface_gml_id
      RENAME_SET_VALUE gml_parent_id > bldg_Building_gml_id
      REMOVE citygml_target_uri
      REMOVE citygml_feature_role
      REMOVE citygml_feature_role_attr_name
      REMOVE citygml_feature_role_attr_val
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE citygml_opening{}.xlink_href
    -> TestFilter_RoofSurface
TestFilter_RoofSurface
    DEFAULT_VALUE = <UNFILTERED>
    PASSED_TEST_GROUP_OUTPUT = FIRST
    TEST_LIST = "BOOL_OP,OR,COMPOSITE_TEST,""""""1"""""",TEST_CLAUSE,CASE_INSENSITIVE_TEST @Value(_geometory_lod) = 2",lod2_RoofSurface,"BOOL_OP,OR,COMPOSITE_TEST,""""""1"""""",TEST_CLAUSE,CASE_INSENSITIVE_TEST @Value(_geometory_lod) = 3",lod3_RoofSurface
    lod2_RoofSurface -> lod2_RoofSurface (writer GEODATABASE_FILE_1)
    lod3_RoofSurface -> lod3_RoofSurface (writer GEODATABASE_FILE_1)
Deaggregator_OuterFloorSurface
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> ListElementCounter_OuterFloorSurface
ListElementCounter_OuterFloorSurface
    CNT_ATTR = _lodCnt
    LIST_NAME = citygml_level_of_detail{}
    -> AttributeCreator_OuterFloorSurface
AttributeCreator_OuterFloorSurface
    ATTR_TABLE = SET_TO _geometory_lod = FME_CONDITIONAL:DEFAULT_VALUE'@Value(citygml_level_of_detail{@sum(@Value(_lodCnt),-1)})'BOOL_OP;OR;COMPOSITE_TEST;1;TEST @Value(_part_number) < @sum(@Value(_lodCnt),-1)'@Value(citygml_level_of_detail{@Value(_part_number)})'FME_NUM_CONDITIONS2___
    -> AttributeManager_OuterFloorSurface
AttributeManager_OuterFloorSurface
    ATTR_TABLE:
      RENAME_SET_VALUE gml_id > bldg_OuterFloorSurface_gml_id
      RENAME_SET_VALUE gml_parent_id > bldg_Building_gml_id
      REMOVE citygml_target_uri
      REMOVE citygml_feature_role
      REMOVE citygml_feature_role_attr_name
      REMOVE citygml_feature_role_attr_val
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE citygml_opening{}.xlink_href
    -> TestFilter_OuterFloorSurface
TestFilter_OuterFloorSurface
    DEFAULT_VALUE = <UNFILTERED>
    PASSED_TEST_GROUP_OUTPUT = FIRST
    TEST_LIST = "BOOL_OP,OR,COMPOSITE_TEST,""""""1"""""",TEST_CLAUSE,CASE_INSENSITIVE_TEST @Value(_geometory_lod) = 2",lod2_OuterFloorSurface,"BOOL_OP,OR,COMPOSITE_TEST,""""""1"""""",TEST_CLAUSE,CASE_INSENSITIVE_TEST @Value(_geometory_lod) = 3",lod3_OuterFloorSurface
    lod2_OuterFloorSurface -> lod2_OuterFloorSurface (writer GEODATABASE_FILE_1)
    lod3_OuterFloorSurface -> lod3_OuterFloorSurface (writer GEODATABASE_FILE_1)
AttributeManager_OuterCeilingSurface
    ATTR_TABLE:
      RENAME_SET_VALUE gml_id > bldg_OuterCeilingSurface_gml_id
      RENAME_SET_VALUE gml_parent_id > bldg_Building_gml_id
      REMOVE citygml_target_uri
      REMOVE citygml_feature_role
      REMOVE citygml_feature_role_attr_name
      REMOVE citygml_feature_role_attr_val
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE citygml_opening{}.xlink_href
    -> lod3_OuterCeilingSurface (writer GEODATABASE_FILE_1)
Deaggregator_GroundSurface
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> ListElementCounter_GroundSurface
ListElementCounter_GroundSurface
    CNT_ATTR = _lodCnt
    LIST_NAME = citygml_level_of_detail{}
    -> AttributeCreator_GroundSurface
AttributeCreator_GroundSurface
    ATTR_TABLE = SET_TO _geometory_lod = FME_CONDITIONAL:DEFAULT_VALUE'@Value(citygml_level_of_detail{@sum(@Value(_lodCnt),-1)})'BOOL_OP;OR;COMPOSITE_TEST;1;TEST @Value(_part_number) < @sum(@Value(_lodCnt),-1)'@Value(citygml_level_of_detail{@Value(_part_number)})'FME_NUM_CONDITIONS2___
    -> AttributeManager_GroundSurface
AttributeManager_GroundSurface
    ATTR_TABLE:
      RENAME_SET_VALUE gml_id > bldg_GroundSurface_gml_id
      RENAME_SET_VALUE gml_parent_id > bldg_Building_gml_id
      REMOVE citygml_target_uri
      REMOVE citygml_feature_role
      REMOVE citygml_feature_role_attr_name
      REMOVE citygml_feature_role_attr_val
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE citygml_opening{}.xlink_href
    -> TestFilter_GroundSurface
TestFilter_GroundSurface
    DEFAULT_VALUE = <UNFILTERED>
    PASSED_TEST_GROUP_OUTPUT = FIRST
    TEST_LIST:
      "BOOL_OP,OR,COMPOSITE_TEST,""""""1 OR 2"""""",TEST_CLAUSE,CASE_INSENSITIVE_TEST @Value(_geometry_name) BEGINS_WITH lod2
      CASE_INSENSITIVE_TEST @Value(_geometry_name) = surfaceMember",lod2_GroundSurface,"BOOL_OP,OR,COMPOSITE_TEST,""""""1"""""",TEST_CLAUSE,CASE_INSENSITIVE_TEST @Value(_geometry_name) BEGINS_WITH lod3",lod3_GroundSurface
    lod2_GroundSurface -> lod2_GroundSurface (writer GEODATABASE_FILE_1)
    lod3_GroundSurface -> lod3_GroundSurface (writer GEODATABASE_FILE_1)
AttributeManager_Door
    ATTR_TABLE:
      RENAME_SET_VALUE gml_id > bldg_Door_gml_id
      RENAME_SET_VALUE gml_parent_id > bldg_Building_gml_id
      REMOVE citygml_target_uri
      REMOVE citygml_feature_role
      REMOVE citygml_feature_role_attr_name
      REMOVE citygml_feature_role_attr_val
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE citygml_address{}.xlink_href
    -> lod3_Door (writer GEODATABASE_FILE_1)
XMLFlattener
    ATTRIBUTE_XML = citygml_address
    EMBEDDED_EXPRESSIONS = xAL:AddressDetails
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    XML_SOURCE_TYPE = Attribute with XML document
    -> XMLFlattener_2
XMLFlattener_2
    ATTRIBUTE_XML = citygml_address
    EMBEDDED_EXPRESSIONS = xAL:Country/xAL:Locality/xAL:LocalityName
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    XML_SOURCE_TYPE = Attribute with XML document
    -> AttributeExposer
AttributeExposer
    ATTR_LIST = LocalityName
    -> AttributeRenamer
AttributeRenamer
    ATTR_TABLE = RENAME_SET_DEFAULT LocalityName > Attribute
    MISSING_INPUT_ATTRS = REMOVE
    -> AttributeExposer_2
AttributeExposer_2
    ATTR_LIST = Address
    -> FeatureJoiner_BuildingPart [RIGHT]
    -> FeatureJoiner_Building [RIGHT]
FeatureJoiner_BuildingPart
    ATTR_CONFLICT_RES = Prefer Left
    GEOMETRY_HANDLING = Prefer Left
    JOIN_KEYS = gml_id gml_parent_id AUTO
    JOIN_MODE = Left
    JOINED -> AttributeCreator_BuildingPart
AttributeCreator_BuildingPart
    ATTR_TABLE:
      SET_TO bldg_usage1 = @Value(citygml_usage{0})
      SET_TO bldg_usage2 = @Value(citygml_usage{1})
      SET_TO bldg_usage3 = @Value(citygml_usage{2})
      SET_TO bldg_usage4 = @Value(citygml_usage{3})
      SET_TO bldg_usage5 = @Value(citygml_usage{4})
      SET_TO bldg_usage6 = @Value(citygml_usage{5})
      SET_TO bldg_usage7 = @Value(citygml_usage{6})
      SET_TO bldg_usage8 = @Value(citygml_usage{7})
      SET_TO bldg_usage9 = @Value(citygml_usage{8})
      SET_TO bldg_usage10 = @Value(citygml_usage{9})
      SET_TO uro_buildingIDAttribute_buildingID = @Value(uro_building_idattribute{0}.uro_building_idattribute_uro_building_id)
      SET_TO uro_buildingIDAttribute_branchID = @Value(uro_building_idattribute{0}.uro_building_idattribute_uro_branch_id)
      SET_TO uro_buildingIDAttribute_partID = @Value(uro_building_idattribute{0}.uro_building_idattribute_uro_part_id)
      SET_TO uro_buildingIDAttribute_prefecture = @Value(uro_building_idattribute{0}.uro_building_idattribute_uro_prefecture)
      SET_TO uro_buildingIDAttribute_city = @Value(uro_building_idattribute{0}.uro_building_idattribute_uro_city)
      SET_TO uro_BuildingDetailAttribute_serialNumberOfBuildingCertification = @Value(uro_building_detail_attribute{0}.uro_building_detail_attribute_uro_serial_number_of_building_certification)
      SET_TO uro_BuildingDetailAttribute_siteArea = @Value(uro_building_detail_attribute{0}.uro_building_detail_attribute_uro_site_area)
      SET_TO uro_BuildingDetailAttribute_totalFloorArea = @Value(uro_building_detail_attribute{0}.uro_building_detail_attribute_uro_total_floor_area)
      SET_TO uro_BuildingDetailAttribute_buildingFootprintArea = @Value(uro_building_detail_attribute{0}.uro_building_detail_attribute_uro_building_footprint_area)
      SET_TO uro_BuildingDetailAttribute_buildingRoofEdgeArea = @Value(uro_building_detail_attribute{0}.uro_building_detail_attribute_uro_building_roof_edge_area)
      SET_TO uro_BuildingDetailAttribute_developmentArea = @Value(uro_building_detail_attribute{0}.uro_building_detail_attribute_uro_development_area)
      SET_TO uro_BuildingDetailAttribute_buildingStructureType = @Value(uro_building_detail_attribute{0}.uro_building_detail_attribute_uro_building_structure_type)
      SET_TO uro_BuildingDetailAttribute_buildingStructureOrgType = @Value(uro_building_detail_attribute{0}.uro_building_detail_attribute_uro_building_structure_org_type)
      SET_TO uro_BuildingDetailAttribute_fireproofStructureType = @Value(uro_building_detail_attribute{0}.uro_building_detail_attribute_uro_fireproof_structure_type)
      SET_TO uro_BuildingDetailAttribute_implementingBody = @Value(uro_building_detail_attribute{0}.uro_building_detail_attribute_uro_implementing_body)
      SET_TO uro_BuildingDetailAttribute_urbanPlanType = @Value(uro_building_detail_attribute{0}.uro_building_detail_attribute_uro_urban_plan_type)
      SET_TO uro_BuildingDetailAttribute_areaClassificationType = @Value(uro_building_detail_attribute{0}.uro_building_detail_attribute_uro_area_classification_type)
      SET_TO uro_BuildingDetailAttribute_districtsAndZonesType1 = @Value(uro_building_detail_attribute{0}.uro_building_detail_attribute_uro_districts_and_zones_type{0})
      SET_TO uro_BuildingDetailAttribute_districtsAndZonesType2 = @Value(uro_building_detail_attribute{0}.uro_building_detail_attribute_uro_districts_and_zones_type{1})
      SET_TO uro_BuildingDetailAttribute_districtsAndZonesType3 = @Value(uro_building_detail_attribute{0}.uro_building_detail_attribute_uro_districts_and_zones_type{2})
      SET_TO uro_BuildingDetailAttribute_districtsAndZonesType4 = @Value(uro_building_detail_attribute{0}.uro_building_detail_attribute_uro_districts_and_zones_type{3})
      SET_TO uro_BuildingDetailAttribute_districtsAndZonesType5 = @Value(uro_building_detail_attribute{0}.uro_building_detail_attribute_uro_districts_and_zones_type{4})
      SET_TO uro_BuildingDetailAttribute_districtsAndZonesType6 = @Value(uro_building_detail_attribute{0}.uro_building_detail_attribute_uro_districts_and_zones_type{5})
      SET_TO uro_BuildingDetailAttribute_districtsAndZonesType7 = @Value(uro_building_detail_attribute{0}.uro_building_detail_attribute_uro_districts_and_zones_type{6})
      SET_TO uro_BuildingDetailAttribute_districtsAndZonesType8 = @Value(uro_building_detail_attribute{0}.uro_building_detail_attribute_uro_districts_and_zones_type{7})
      SET_TO uro_BuildingDetailAttribute_districtsAndZonesType9 = @Value(uro_building_detail_attribute{0}.uro_building_detail_attribute_uro_districts_and_zones_type{8})
      SET_TO uro_BuildingDetailAttribute_districtsAndZonesType10 = @Value(uro_building_detail_attribute{0}.uro_building_detail_attribute_uro_districts_and_zones_type{9})
      SET_TO uro_BuildingDetailAttribute_landUseType = @Value(uro_building_detail_attribute{0}.uro_building_detail_attribute_uro_land_use_type)
      SET_TO uro_BuildingDetailAttribute_reference = @Value(uro_building_detail_attribute{0}.uro_building_detail_attribute_uro_reference)
      SET_TO uro_BuildingDetailAttribute_majorUsage = @Value(uro_building_detail_attribute{0}.uro_building_detail_attribute_uro_major_usage)
      SET_TO uro_BuildingDetailAttribute_majorUsage2 = @Value(uro_building_detail_attribute{0}.uro_building_detail_attribute_uro_major_usage2)
      SET_TO uro_BuildingDetailAttribute_orgUsage = @Value(uro_building_detail_attribute{0}.uro_building_detail_attribute_uro_org_usage)
      SET_TO uro_BuildingDetailAttribute_orgUsage2 = @Value(uro_building_detail_attribute{0}.uro_building_detail_attribute_uro_org_usage2)
      SET_TO uro_BuildingDetailAttribute_detailedUsage = @Value(uro_building_detail_attribute{0}.uro_building_detail_attribute_uro_detailed_usage)
      SET_TO uro_BuildingDetailAttribute_detailedUsage2 = @Value(uro_building_detail_attribute{0}.uro_building_detail_attribute_uro_detailed_usage2)
      SET_TO uro_BuildingDetailAttribute_detailedUsage3 = @Value(uro_building_detail_attribute{0}.uro_building_detail_attribute_uro_detailed_usage3)
      SET_TO uro_BuildingDetailAttribute_groundFloorUsage = @Value(uro_building_detail_attribute{0}.uro_building_detail_attribute_uro_ground_floor_usage)
      SET_TO uro_BuildingDetailAttribute_secondFloorUsage = @Value(uro_building_detail_attribute{0}.uro_building_detail_attribute_uro_second_floor_usage)
      SET_TO uro_BuildingDetailAttribute_thirdFloorUsage = @Value(uro_building_detail_attribute{0}.uro_building_detail_attribute_uro_third_floor_usage)
      SET_TO uro_BuildingDetailAttribute_basementUsage = @Value(uro_building_detail_attribute{0}.uro_building_detail_attribute_uro_basement_usage)
      SET_TO uro_BuildingDetailAttribute_basementFirstUsage = @Value(uro_building_detail_attribute{0}.uro_building_detail_attribute_uro_basement_first_usage)
      SET_TO uro_BuildingDetailAttribute_basementSecondUsage = @Value(uro_building_detail_attribute{0}.uro_building_detail_attribute_uro_basement_second_usage)
      SET_TO uro_BuildingDetailAttribute_vacancy = @Value(uro_building_detail_attribute{0}.uro_building_detail_attribute_uro_vacancy)
      SET_TO uro_BuildingDetailAttribute_buildingCoverageRate = @Value(uro_building_detail_attribute{0}.uro_building_detail_attribute_uro_building_coverage_rate)
      SET_TO uro_BuildingDetailAttribute_floorAreaRate = @Value(uro_building_detail_attribute{0}.uro_building_detail_attribute_uro_floor_area_rate)
      SET_TO uro_BuildingDetailAttribute_specifiedBuildingCoverageRate = @Value(uro_building_detail_attribute{0}.uro_building_detail_attribute_uro_specified_building_coverage_rate)
      SET_TO uro_BuildingDetailAttribute_specifiedFloorAreaRate = @Value(uro_building_detail_attribute{0}.uro_building_detail_attribute_uro_specified_floor_area_rate)
      SET_TO uro_BuildingDetailAttribute_standardFloorAreaRate = @Value(uro_building_detail_attribute{0}.uro_building_detail_attribute_uro_standard_floor_area_rate)
      SET_TO uro_BuildingDetailAttribute_buildingHeight = @Value(uro_building_detail_attribute{0}.uro_building_detail_attribute_uro_building_height)
      SET_TO uro_BuildingDetailAttribute_eaveHeight = @Value(uro_building_detail_attribute{0}.uro_building_detail_attribute_uro_eave_height)
      SET_TO uro_BuildingDetailAttribute_note = @Value(uro_building_detail_attribute{0}.uro_building_detail_attribute_uro_note)
      SET_TO uro_BuildingDetailAttribute_surveyYear = @Value(uro_building_detail_attribute{0}.uro_building_detail_attribute_uro_survey_year)
      SET_TO uro_buildingIDAttribute = @Value(gml_parent_id)
    -> AttributeManager_BuildingPart
AttributeManager_BuildingPart
    ATTR_TABLE:
      RENAME_SET_VALUE gml_id > bldg_BuildingPart_gml_id
      RENAME_SET_VALUE gml_parent_id > bldg_Building_gml_id
      REMOVE citygml_target_uri
      REMOVE citygml_feature_role
      REMOVE citygml_feature_role_attr_name
      REMOVE citygml_feature_role_attr_val
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      RENAME_SET_VALUE citygml_class > bldg_class
      REMOVE citygml_class_codeSpace
      REMOVE citygml_function{}
      REMOVE citygml_function{}.codeSpace
      REMOVE citygml_usage{}
      REMOVE citygml_usage{}.codeSpace
      RENAME_SET_VALUE citygml_year_of_construction > bldg_yearOfConstruction
      RENAME_SET_VALUE citygml_year_of_demolition > bldg_yearOfDemolition
      RENAME_SET_VALUE citygml_roof_type > bldg_roofType
      REMOVE citygml_roof_type_codeSpace
      RENAME_SET_VALUE citygml_measured_height > bldg_measuredHeight
      REMOVE citygml_measured_height_units
      RENAME_SET_VALUE citygml_storeys_above_ground > bldg_storeysAboveGround
      RENAME_SET_VALUE citygml_storeys_below_ground > bldg_storeysBelowGround
      RENAME_SET_VALUE citygml_storey_heights_above_ground > bldg_storeyHeightsAboveGround
      REMOVE citygml_storey_heights_above_ground_units
      RENAME_SET_VALUE citygml_storey_heights_below_ground > bldg_storeyHeightsBelowGround
      REMOVE citygml_storey_heights_below_ground_units
      REMOVE citygml_outer_building_installation{}.xlink_href
      REMOVE citygml_interior_building_installation{}.xlink_href
      REMOVE citygml_bounded_by{}.xlink_href
      REMOVE citygml_level_of_detail{}
      REMOVE citygml_interior_room{}.xlink_href
      REMOVE citygml_consists_of_building_part{}.xlink_href
      REMOVE citygml_address{}.xlink_href
      REMOVE uro_building_data_quality_attribute{}.uro_building_data_quality_attribute_uro_src_scale{}
      REMOVE uro_building_data_quality_attribute{}.uro_building_data_quality_attribute_uro_src_scale{}.codeSpace
      REMOVE uro_building_data_quality_attribute{}.uro_building_data_quality_attribute_uro_geometry_src_desc{}
      REMOVE uro_building_data_quality_attribute{}.uro_building_data_quality_attribute_uro_geometry_src_desc{}.codeSpace
      REMOVE uro_building_data_quality_attribute{}.uro_building_data_quality_attribute_uro_thematic_src_desc{}
      REMOVE uro_building_data_quality_attribute{}.uro_building_data_quality_attribute_uro_thematic_src_desc{}.codeSpace
      REMOVE uro_building_data_quality_attribute{}.uro_building_data_quality_attribute_uro_appearance_src_desc{}
      REMOVE uro_building_data_quality_attribute{}.uro_building_data_quality_attribute_uro_appearance_src_desc{}.codeSpace
      REMOVE uro_building_data_quality_attribute{}.uro_building_data_quality_attribute_uro_lod1_height_type
      REMOVE uro_building_data_quality_attribute{}.uro_building_data_quality_attribute_uro_lod1_height_type_codeSpace
      REMOVE uro_building_data_quality_attribute{}.uro_building_data_quality_attribute_uro_lod_type{}
      REMOVE uro_building_detail_attribute{}.uro_building_detail_attribute_uro_serial_number_of_building_certification
      REMOVE uro_building_detail_attribute{}.uro_building_detail_attribute_uro_site_area
      REMOVE uro_building_detail_attribute{}.uro_building_detail_attribute_uro_site_area_units
      REMOVE uro_building_detail_attribute{}.uro_building_detail_attribute_uro_total_floor_area
      REMOVE uro_building_detail_attribute{}.uro_building_detail_attribute_uro_total_floor_area_units
      REMOVE uro_building_detail_attribute{}.uro_building_detail_attribute_uro_building_footprint_area
      REMOVE uro_building_detail_attribute{}.uro_building_detail_attribute_uro_building_footprint_area_units
      REMOVE uro_building_detail_attribute{}.uro_building_detail_attribute_uro_building_roof_edge_area
      REMOVE uro_building_detail_attribute{}.uro_building_detail_attribute_uro_building_roof_edge_area_units
      REMOVE uro_building_detail_attribute{}.uro_building_detail_attribute_uro_development_area
      REMOVE uro_building_detail_attribute{}.uro_building_detail_attribute_uro_development_area_units
      REMOVE uro_building_detail_attribute{}.uro_building_detail_attribute_uro_building_structure_type
      REMOVE uro_building_detail_attribute{}.uro_building_detail_attribute_uro_building_structure_type_codeSpace
      REMOVE uro_building_detail_attribute{}.uro_building_detail_attribute_uro_building_structure_org_type
      REMOVE uro_building_detail_attribute{}.uro_building_detail_attribute_uro_building_structure_org_type_codeSpace
      REMOVE uro_building_detail_attribute{}.uro_building_detail_attribute_uro_fireproof_structure_type
      REMOVE uro_building_detail_attribute{}.uro_building_detail_attribute_uro_fireproof_structure_type_codeSpace
      REMOVE uro_building_detail_attribute{}.uro_building_detail_attribute_uro_implementing_body
      REMOVE uro_building_detail_attribute{}.uro_building_detail_attribute_uro_urban_plan_type
      REMOVE uro_building_detail_attribute{}.uro_building_detail_attribute_uro_urban_plan_type_codeSpace
      REMOVE uro_building_detail_attribute{}.uro_building_detail_attribute_uro_area_classification_type
      REMOVE uro_building_detail_attribute{}.uro_building_detail_attribute_uro_area_classification_type_codeSpace
      REMOVE uro_building_detail_attribute{}.uro_building_detail_attribute_uro_districts_and_zones_type{}
      REMOVE uro_building_detail_attribute{}.uro_building_detail_attribute_uro_districts_and_zones_type{}.codeSpace
      REMOVE uro_building_detail_attribute{}.uro_building_detail_attribute_uro_land_use_type
      REMOVE uro_building_detail_attribute{}.uro_building_detail_attribute_uro_land_use_type_codeSpace
      REMOVE uro_building_detail_attribute{}.uro_building_detail_attribute_uro_reference
      REMOVE uro_building_detail_attribute{}.uro_building_detail_attribute_uro_major_usage
      REMOVE uro_building_detail_attribute{}.uro_building_detail_attribute_uro_major_usage_codeSpace
      REMOVE uro_building_detail_attribute{}.uro_building_detail_attribute_uro_major_usage2
      REMOVE uro_building_detail_attribute{}.uro_building_detail_attribute_uro_major_usage2_codeSpace
      REMOVE uro_building_detail_attribute{}.uro_building_detail_attribute_uro_org_usage
      REMOVE uro_building_detail_attribute{}.uro_building_detail_attribute_uro_org_usage_codeSpace
      REMOVE uro_building_detail_attribute{}.uro_building_detail_attribute_uro_org_usage2
      REMOVE uro_building_detail_attribute{}.uro_building_detail_attribute_uro_org_usage2_codeSpace
      REMOVE uro_building_detail_attribute{}.uro_building_detail_attribute_uro_detailed_usage
      REMOVE uro_building_detail_attribute{}.uro_building_detail_attribute_uro_detailed_usage_codeSpace
      REMOVE uro_building_detail_attribute{}.uro_building_detail_attribute_uro_detailed_usage2
      REMOVE uro_building_detail_attribute{}.uro_building_detail_attribute_uro_detailed_usage2_codeSpace
      REMOVE uro_building_detail_attribute{}.uro_building_detail_attribute_uro_detailed_usage3
      REMOVE uro_building_detail_attribute{}.uro_building_detail_attribute_uro_detailed_usage3_codeSpace
      REMOVE uro_building_detail_attribute{}.uro_building_detail_attribute_uro_ground_floor_usage
      REMOVE uro_building_detail_attribute{}.uro_building_detail_attribute_uro_ground_floor_usage_codeSpace
      REMOVE uro_building_detail_attribute{}.uro_building_detail_attribute_uro_second_floor_usage
      REMOVE uro_building_detail_attribute{}.uro_building_detail_attribute_uro_second_floor_usage_codeSpace
      REMOVE uro_building_detail_attribute{}.uro_building_detail_attribute_uro_third_floor_usage
      REMOVE uro_building_detail_attribute{}.uro_building_detail_attribute_uro_third_floor_usage_codeSpace
      REMOVE uro_building_detail_attribute{}.uro_building_detail_attribute_uro_basement_usage
      REMOVE uro_building_detail_attribute{}.uro_building_detail_attribute_uro_basement_usage_codeSpace
      REMOVE uro_building_detail_attribute{}.uro_building_detail_attribute_uro_basement_first_usage
      REMOVE uro_building_detail_attribute{}.uro_building_detail_attribute_uro_basement_first_usage_codeSpace
      REMOVE uro_building_detail_attribute{}.uro_building_detail_attribute_uro_basement_second_usage
      REMOVE uro_building_detail_attribute{}.uro_building_detail_attribute_uro_basement_second_usage_codeSpace
      REMOVE uro_building_detail_attribute{}.uro_building_detail_attribute_uro_vacancy
      REMOVE uro_building_detail_attribute{}.uro_building_detail_attribute_uro_vacancy_codeSpace
      REMOVE uro_building_detail_attribute{}.uro_building_detail_attribute_uro_building_coverage_rate
      REMOVE uro_building_detail_attribute{}.uro_building_detail_attribute_uro_floor_area_rate
      REMOVE uro_building_detail_attribute{}.uro_building_detail_attribute_uro_specified_building_coverage_rate
      REMOVE uro_building_detail_attribute{}.uro_building_detail_attribute_uro_specified_floor_area_rate
      REMOVE uro_building_detail_attribute{}.uro_building_detail_attribute_uro_standard_floor_area_rate
      REMOVE uro_building_detail_attribute{}.uro_building_detail_attribute_uro_building_height
      REMOVE uro_building_detail_attribute{}.uro_building_detail_attribute_uro_building_height_units
      REMOVE uro_building_detail_attribute{}.uro_building_detail_attribute_uro_eave_height
      REMOVE uro_building_detail_attribute{}.uro_building_detail_attribute_uro_eave_height_units
      REMOVE uro_building_detail_attribute{}.uro_building_detail_attribute_uro_note
      REMOVE uro_building_detail_attribute{}.uro_building_detail_attribute_uro_survey_year
      REMOVE uro_building_disaster_risk_attribute{}.uro_building_high_tide_risk_attribute_uro_description
      REMOVE uro_building_disaster_risk_attribute{}.uro_building_high_tide_risk_attribute_uro_description_codeSpace
      REMOVE uro_building_disaster_risk_attribute{}.uro_building_high_tide_risk_attribute_uro_rank
      REMOVE uro_building_disaster_risk_attribute{}.uro_building_high_tide_risk_attribute_uro_rank_codeSpace
      REMOVE uro_building_disaster_risk_attribute{}.uro_building_high_tide_risk_attribute_uro_rank_org
      REMOVE uro_building_disaster_risk_attribute{}.uro_building_high_tide_risk_attribute_uro_rank_org_codeSpace
      REMOVE uro_building_disaster_risk_attribute{}.uro_building_high_tide_risk_attribute_uro_depth
      REMOVE uro_building_disaster_risk_attribute{}.uro_building_high_tide_risk_attribute_uro_depth_units
      REMOVE uro_building_disaster_risk_attribute{}.uro_building_inland_flooding_risk_attribute_uro_description
      REMOVE uro_building_disaster_risk_attribute{}.uro_building_inland_flooding_risk_attribute_uro_description_codeSpace
      REMOVE uro_building_disaster_risk_attribute{}.uro_building_inland_flooding_risk_attribute_uro_rank
      REMOVE uro_building_disaster_risk_attribute{}.uro_building_inland_flooding_risk_attribute_uro_rank_codeSpace
      REMOVE uro_building_disaster_risk_attribute{}.uro_building_inland_flooding_risk_attribute_uro_rank_org
      REMOVE uro_building_disaster_risk_attribute{}.uro_building_inland_flooding_risk_attribute_uro_rank_org_codeSpace
      REMOVE uro_building_disaster_risk_attribute{}.uro_building_inland_flooding_risk_attribute_uro_depth
      REMOVE uro_building_disaster_risk_attribute{}.uro_building_inland_flooding_risk_attribute_uro_depth_units
      REMOVE uro_building_disaster_risk_attribute{}.uro_building_land_slide_risk_attribute_uro_description
      REMOVE uro_building_disaster_risk_attribute{}.uro_building_land_slide_risk_attribute_uro_description_codeSpace
      REMOVE uro_building_disaster_risk_attribute{}.uro_building_land_slide_risk_attribute_uro_area_type
      REMOVE uro_building_disaster_risk_attribute{}.uro_building_land_slide_risk_attribute_uro_area_type_codeSpace
      REMOVE uro_building_disaster_risk_attribute{}.uro_building_river_flooding_risk_attribute_uro_description
      REMOVE uro_building_disaster_risk_attribute{}.uro_building_river_flooding_risk_attribute_uro_description_codeSpace
      REMOVE uro_building_disaster_risk_attribute{}.uro_building_river_flooding_risk_attribute_uro_rank
      REMOVE uro_building_disaster_risk_attribute{}.uro_building_river_flooding_risk_attribute_uro_rank_codeSpace
      REMOVE uro_building_disaster_risk_attribute{}.uro_building_river_flooding_risk_attribute_uro_rank_org
      REMOVE uro_building_disaster_risk_attribute{}.uro_building_river_flooding_risk_attribute_uro_rank_org_codeSpace
      REMOVE uro_building_disaster_risk_attribute{}.uro_building_river_flooding_risk_attribute_uro_depth
      REMOVE uro_building_disaster_risk_attribute{}.uro_building_river_flooding_risk_attribute_uro_depth_units
      REMOVE uro_building_disaster_risk_attribute{}.uro_building_river_flooding_risk_attribute_uro_admin_type
      REMOVE uro_building_disaster_risk_attribute{}.uro_building_river_flooding_risk_attribute_uro_admin_type_codeSpace
      REMOVE uro_building_disaster_risk_attribute{}.uro_building_river_flooding_risk_attribute_uro_scale
      REMOVE uro_building_disaster_risk_attribute{}.uro_building_river_flooding_risk_attribute_uro_scale_codeSpace
      REMOVE uro_building_disaster_risk_attribute{}.uro_building_river_flooding_risk_attribute_uro_duration
      REMOVE uro_building_disaster_risk_attribute{}.uro_building_river_flooding_risk_attribute_uro_duration_units
      REMOVE uro_building_disaster_risk_attribute{}.uro_building_tsunami_risk_attribute_uro_description
      REMOVE uro_building_disaster_risk_attribute{}.uro_building_tsunami_risk_attribute_uro_description_codeSpace
      REMOVE uro_building_disaster_risk_attribute{}.uro_building_tsunami_risk_attribute_uro_rank
      REMOVE uro_building_disaster_risk_attribute{}.uro_building_tsunami_risk_attribute_uro_rank_codeSpace
      REMOVE uro_building_disaster_risk_attribute{}.uro_building_tsunami_risk_attribute_uro_rank_org
      REMOVE uro_building_disaster_risk_attribute{}.uro_building_tsunami_risk_attribute_uro_rank_org_codeSpace
      REMOVE uro_building_disaster_risk_attribute{}.uro_building_tsunami_risk_attribute_uro_depth
      REMOVE uro_building_disaster_risk_attribute{}.uro_building_tsunami_risk_attribute_uro_depth_units
      REMOVE uro_building_idattribute{}.uro_building_idattribute_uro_building_id
      REMOVE uro_building_idattribute{}.uro_building_idattribute_uro_branch_id
      REMOVE uro_building_idattribute{}.uro_building_idattribute_uro_part_id
      REMOVE uro_building_idattribute{}.uro_building_idattribute_uro_prefecture
      REMOVE uro_building_idattribute{}.uro_building_idattribute_uro_prefecture_codeSpace
      REMOVE uro_building_idattribute{}.uro_building_idattribute_uro_city
      REMOVE uro_building_idattribute{}.uro_building_idattribute_uro_city_codeSpace
      REMOVE uro_key_value_pair_attribute{}.uro_key_value_pair_attribute_uro_key
      REMOVE uro_key_value_pair_attribute{}.uro_key_value_pair_attribute_uro_key_codeSpace
      REMOVE uro_key_value_pair_attribute{}.uro_key_value_pair_attribute_uro_code_value
      REMOVE uro_key_value_pair_attribute{}.uro_key_value_pair_attribute_uro_code_value_codeSpace
      REMOVE uro_key_value_pair_attribute{}.uro_key_value_pair_attribute_uro_string_value
      REMOVE uro_key_value_pair_attribute{}.uro_key_value_pair_attribute_uro_int_value
      REMOVE uro_key_value_pair_attribute{}.uro_key_value_pair_attribute_uro_double_value
      REMOVE uro_key_value_pair_attribute{}.uro_key_value_pair_attribute_uro_measured_value
      REMOVE uro_key_value_pair_attribute{}.uro_key_value_pair_attribute_uro_measured_value_units
      REMOVE uro_key_value_pair_attribute{}.uro_key_value_pair_attribute_uro_date_value
      REMOVE uro_key_value_pair_attribute{}.uro_key_value_pair_attribute_uro_uri_value
      REMOVE uro_large_customer_facility_attribute{}.uro_large_customer_facility_attribute_uro_class
      REMOVE uro_large_customer_facility_attribute{}.uro_large_customer_facility_attribute_uro_class_codeSpace
      REMOVE uro_large_customer_facility_attribute{}.uro_large_customer_facility_attribute_uro_name
      REMOVE uro_large_customer_facility_attribute{}.uro_large_customer_facility_attribute_uro_capacity
      REMOVE uro_large_customer_facility_attribute{}.uro_large_customer_facility_attribute_uro_owner
      REMOVE uro_large_customer_facility_attribute{}.uro_large_customer_facility_attribute_uro_total_floor_area
      REMOVE uro_large_customer_facility_attribute{}.uro_large_customer_facility_attribute_uro_total_floor_area_units
      REMOVE uro_large_customer_facility_attribute{}.uro_large_customer_facility_attribute_uro_total_store_floor_area
      REMOVE uro_large_customer_facility_attribute{}.uro_large_customer_facility_attribute_uro_total_store_floor_area_units
      REMOVE uro_large_customer_facility_attribute{}.uro_large_customer_facility_attribute_uro_inaugural_date
      REMOVE uro_large_customer_facility_attribute{}.uro_large_customer_facility_attribute_uro_key_tenants
      REMOVE uro_large_customer_facility_attribute{}.uro_large_customer_facility_attribute_uro_availability
      REMOVE uro_large_customer_facility_attribute{}.uro_large_customer_facility_attribute_uro_urban_plan_type
      REMOVE uro_large_customer_facility_attribute{}.uro_large_customer_facility_attribute_uro_urban_plan_type_codeSpace
      REMOVE uro_large_customer_facility_attribute{}.uro_large_customer_facility_attribute_uro_area_classification_type
      REMOVE uro_large_customer_facility_attribute{}.uro_large_customer_facility_attribute_uro_area_classification_type_codeSpace
      REMOVE uro_large_customer_facility_attribute{}.uro_large_customer_facility_attribute_uro_districts_and_zones_type{}
      REMOVE uro_large_customer_facility_attribute{}.uro_large_customer_facility_attribute_uro_districts_and_zones_type{}.codeSpace
      REMOVE uro_large_customer_facility_attribute{}.uro_large_customer_facility_attribute_uro_land_use_type
      REMOVE uro_large_customer_facility_attribute{}.uro_large_customer_facility_attribute_uro_land_use_type_codeSpace
      REMOVE uro_large_customer_facility_attribute{}.uro_large_customer_facility_attribute_uro_reference
      REMOVE uro_large_customer_facility_attribute{}.uro_large_customer_facility_attribute_uro_note
      REMOVE uro_large_customer_facility_attribute{}.uro_large_customer_facility_attribute_uro_survey_year
      REMOVE Attribute
      REMOVE citygml_address
      RENAME_SET_VALUE Address > bldg_address
    USER_EXPOSED_ATTRIBUTES = Definition.id
    -> FeatureJoiner_BuildingPart_2 [LEFT]
FeatureJoiner_Building
    ATTR_CONFLICT_RES = Prefer Left
    GEOMETRY_HANDLING = Prefer Left
    JOIN_KEYS = gml_id gml_parent_id AUTO
    JOIN_MODE = Left
    JOINED -> AttributeCreator_Building
AttributeCreator_Building
    ATTR_TABLE:
      SET_TO bldg_usage1 = @Value(citygml_usage{0})
      SET_TO bldg_usage2 = @Value(citygml_usage{1})
      SET_TO bldg_usage3 = @Value(citygml_usage{2})
      SET_TO bldg_usage4 = @Value(citygml_usage{3})
      SET_TO bldg_usage5 = @Value(citygml_usage{4})
      SET_TO bldg_usage6 = @Value(citygml_usage{5})
      SET_TO bldg_usage7 = @Value(citygml_usage{6})
      SET_TO bldg_usage8 = @Value(citygml_usage{7})
      SET_TO bldg_usage9 = @Value(citygml_usage{8})
      SET_TO bldg_usage10 = @Value(citygml_usage{9})
      SET_TO uro_buildingIDAttribute_buildingID = @Value(uro_building_idattribute{0}.uro_building_idattribute_uro_building_id)
      SET_TO uro_buildingIDAttribute_branchID = @Value(uro_building_idattribute{0}.uro_building_idattribute_uro_branch_id)
      SET_TO uro_buildingIDAttribute_partID = @Value(uro_building_idattribute{0}.uro_building_idattribute_uro_part_id)
      SET_TO uro_buildingIDAttribute_prefecture = @Value(uro_building_idattribute{0}.uro_building_idattribute_uro_prefecture)
      SET_TO uro_buildingIDAttribute_city = @Value(uro_building_idattribute{0}.uro_building_idattribute_uro_city)
      SET_TO uro_BuildingDetailAttribute_serialNumberOfBuildingCertification = @Value(uro_building_detail_attribute{0}.uro_building_detail_attribute_uro_serial_number_of_building_certification)
      SET_TO uro_BuildingDetailAttribute_siteArea = @Value(uro_building_detail_attribute{0}.uro_building_detail_attribute_uro_site_area)
      SET_TO uro_BuildingDetailAttribute_totalFloorArea = @Value(uro_building_detail_attribute{0}.uro_building_detail_attribute_uro_total_floor_area)
      SET_TO uro_BuildingDetailAttribute_buildingFootprintArea = @Value(uro_building_detail_attribute{0}.uro_building_detail_attribute_uro_building_footprint_area)
      SET_TO uro_BuildingDetailAttribute_buildingRoofEdgeArea = @Value(uro_building_detail_attribute{0}.uro_building_detail_attribute_uro_building_roof_edge_area)
      SET_TO uro_BuildingDetailAttribute_developmentArea = @Value(uro_building_detail_attribute{0}.uro_building_detail_attribute_uro_development_area)
      SET_TO uro_BuildingDetailAttribute_buildingStructureType = @Value(uro_building_detail_attribute{0}.uro_building_detail_attribute_uro_building_structure_type)
      SET_TO uro_BuildingDetailAttribute_buildingStructureOrgType = @Value(uro_building_detail_attribute{0}.uro_building_detail_attribute_uro_building_structure_org_type)
      SET_TO uro_BuildingDetailAttribute_fireproofStructureType = @Value(uro_building_detail_attribute{0}.uro_building_detail_attribute_uro_fireproof_structure_type)
      SET_TO uro_BuildingDetailAttribute_implementingBody = @Value(uro_building_detail_attribute{0}.uro_building_detail_attribute_uro_implementing_body)
      SET_TO uro_BuildingDetailAttribute_urbanPlanType = @Value(uro_building_detail_attribute{0}.uro_building_detail_attribute_uro_urban_plan_type)
      SET_TO uro_BuildingDetailAttribute_areaClassificationType = @Value(uro_building_detail_attribute{0}.uro_building_detail_attribute_uro_area_classification_type)
      SET_TO uro_BuildingDetailAttribute_districtsAndZonesType1 = @Value(uro_building_detail_attribute{0}.uro_building_detail_attribute_uro_districts_and_zones_type{0})
      SET_TO uro_BuildingDetailAttribute_districtsAndZonesType2 = @Value(uro_building_detail_attribute{0}.uro_building_detail_attribute_uro_districts_and_zones_type{1})
      SET_TO uro_BuildingDetailAttribute_districtsAndZonesType3 = @Value(uro_building_detail_attribute{0}.uro_building_detail_attribute_uro_districts_and_zones_type{2})
      SET_TO uro_BuildingDetailAttribute_districtsAndZonesType4 = @Value(uro_building_detail_attribute{0}.uro_building_detail_attribute_uro_districts_and_zones_type{3})
      SET_TO uro_BuildingDetailAttribute_districtsAndZonesType5 = @Value(uro_building_detail_attribute{0}.uro_building_detail_attribute_uro_districts_and_zones_type{4})
      SET_TO uro_BuildingDetailAttribute_districtsAndZonesType6 = @Value(uro_building_detail_attribute{0}.uro_building_detail_attribute_uro_districts_and_zones_type{5})
      SET_TO uro_BuildingDetailAttribute_districtsAndZonesType7 = @Value(uro_building_detail_attribute{0}.uro_building_detail_attribute_uro_districts_and_zones_type{6})
      SET_TO uro_BuildingDetailAttribute_districtsAndZonesType8 = @Value(uro_building_detail_attribute{0}.uro_building_detail_attribute_uro_districts_and_zones_type{7})
      SET_TO uro_BuildingDetailAttribute_districtsAndZonesType9 = @Value(uro_building_detail_attribute{0}.uro_building_detail_attribute_uro_districts_and_zones_type{8})
      SET_TO uro_BuildingDetailAttribute_districtsAndZonesType10 = @Value(uro_building_detail_attribute{0}.uro_building_detail_attribute_uro_districts_and_zones_type{9})
      SET_TO uro_BuildingDetailAttribute_landUseType = @Value(uro_building_detail_attribute{0}.uro_building_detail_attribute_uro_land_use_type)
      SET_TO uro_BuildingDetailAttribute_reference = @Value(uro_building_detail_attribute{0}.uro_building_detail_attribute_uro_reference)
      SET_TO uro_BuildingDetailAttribute_majorUsage = @Value(uro_building_detail_attribute{0}.uro_building_detail_attribute_uro_major_usage)
      SET_TO uro_BuildingDetailAttribute_majorUsage2 = @Value(uro_building_detail_attribute{0}.uro_building_detail_attribute_uro_major_usage2)
      SET_TO uro_BuildingDetailAttribute_orgUsage = @Value(uro_building_detail_attribute{0}.uro_building_detail_attribute_uro_org_usage)
      SET_TO uro_BuildingDetailAttribute_orgUsage2 = @Value(uro_building_detail_attribute{0}.uro_building_detail_attribute_uro_org_usage2)
      SET_TO uro_BuildingDetailAttribute_detailedUsage = @Value(uro_building_detail_attribute{0}.uro_building_detail_attribute_uro_detailed_usage)
      SET_TO uro_BuildingDetailAttribute_detailedUsage2 = @Value(uro_building_detail_attribute{0}.uro_building_detail_attribute_uro_detailed_usage2)
      SET_TO uro_BuildingDetailAttribute_detailedUsage3 = @Value(uro_building_detail_attribute{0}.uro_building_detail_attribute_uro_detailed_usage3)
      SET_TO uro_BuildingDetailAttribute_groundFloorUsage = @Value(uro_building_detail_attribute{0}.uro_building_detail_attribute_uro_ground_floor_usage)
      SET_TO uro_BuildingDetailAttribute_secondFloorUsage = @Value(uro_building_detail_attribute{0}.uro_building_detail_attribute_uro_second_floor_usage)
      SET_TO uro_BuildingDetailAttribute_thirdFloorUsage = @Value(uro_building_detail_attribute{0}.uro_building_detail_attribute_uro_third_floor_usage)
      SET_TO uro_BuildingDetailAttribute_basementUsage = @Value(uro_building_detail_attribute{0}.uro_building_detail_attribute_uro_basement_usage)
      SET_TO uro_BuildingDetailAttribute_basementFirstUsage = @Value(uro_building_detail_attribute{0}.uro_building_detail_attribute_uro_basement_first_usage)
      SET_TO uro_BuildingDetailAttribute_basementSecondUsage = @Value(uro_building_detail_attribute{0}.uro_building_detail_attribute_uro_basement_second_usage)
      SET_TO uro_BuildingDetailAttribute_vacancy = @Value(uro_building_detail_attribute{0}.uro_building_detail_attribute_uro_vacancy)
      SET_TO uro_BuildingDetailAttribute_buildingCoverageRate = @Value(uro_building_detail_attribute{0}.uro_building_detail_attribute_uro_building_coverage_rate)
      SET_TO uro_BuildingDetailAttribute_floorAreaRate = @Value(uro_building_detail_attribute{0}.uro_building_detail_attribute_uro_floor_area_rate)
      SET_TO uro_BuildingDetailAttribute_specifiedBuildingCoverageRate = @Value(uro_building_detail_attribute{0}.uro_building_detail_attribute_uro_specified_building_coverage_rate)
      SET_TO uro_BuildingDetailAttribute_specifiedFloorAreaRate = @Value(uro_building_detail_attribute{0}.uro_building_detail_attribute_uro_specified_floor_area_rate)
      SET_TO uro_BuildingDetailAttribute_standardFloorAreaRate = @Value(uro_building_detail_attribute{0}.uro_building_detail_attribute_uro_standard_floor_area_rate)
      SET_TO uro_BuildingDetailAttribute_buildingHeight = @Value(uro_building_detail_attribute{0}.uro_building_detail_attribute_uro_building_height)
      SET_TO uro_BuildingDetailAttribute_eaveHeight = @Value(uro_building_detail_attribute{0}.uro_building_detail_attribute_uro_eave_height)
      SET_TO uro_BuildingDetailAttribute_note = @Value(uro_building_detail_attribute{0}.uro_building_detail_attribute_uro_note)
      SET_TO uro_BuildingDetailAttribute_surveyYear = @Value(uro_building_detail_attribute{0}.uro_building_detail_attribute_uro_survey_year)
      SET_TO uro_LargeCustomerFacilityAttribute_class = @Value(uro_large_customer_facility_attribute{0}.uro_large_customer_facility_attribute_uro_class)
      SET_TO uro_LargeCustomerFacilityAttribute_name = @Value(uro_large_customer_facility_attribute{0}.uro_large_customer_facility_attribute_uro_name)
      SET_TO uro_LargeCustomerFacilityAttribute_capacity = @Value(uro_large_customer_facility_attribute{0}.uro_large_customer_facility_attribute_uro_capacity)
      SET_TO uro_LargeCustomerFacilityAttribute_owner = @Value(uro_large_customer_facility_attribute{0}.uro_large_customer_facility_attribute_uro_owner)
      SET_TO uro_LargeCustomerFacilityAttribute_totalFloorArea = @Value(uro_large_customer_facility_attribute{0}.uro_large_customer_facility_attribute_uro_total_floor_area)
      SET_TO uro_LargeCustomerFacilityAttribute_totalStoreFloorArea = @Value(uro_large_customer_facility_attribute{0}.uro_large_customer_facility_attribute_uro_total_store_floor_area)
      SET_TO uro_LargeCustomerFacilityAttribute_inauguralDate = @Value(uro_large_customer_facility_attribute{0}.uro_large_customer_facility_attribute_uro_inaugural_date)
      SET_TO uro_LargeCustomerFacilityAttribute_keyTenants = @Value(uro_large_customer_facility_attribute{0}.uro_large_customer_facility_attribute_uro_key_tenants)
      SET_TO uro_LargeCustomerFacilityAttribute_availability = @Value(uro_large_customer_facility_attribute{0}.uro_large_customer_facility_attribute_uro_availability)
      SET_TO uro_LargeCustomerFacilityAttribute_urbanPlanType = @Value(uro_large_customer_facility_attribute{0}.uro_large_customer_facility_attribute_uro_urban_plan_type)
      SET_TO uro_LargeCustomerFacilityAttribute_areaClassificationType = @Value(uro_large_customer_facility_attribute{0}.uro_large_customer_facility_attribute_uro_area_classification_type)
      SET_TO uro_LargeCustomerFacilityAttribute_districtsAndZonesType1 = @Value(uro_large_customer_facility_attribute{0}.uro_large_customer_facility_attribute_uro_districts_and_zones_type{0})
      SET_TO uro_LargeCustomerFacilityAttribute_districtsAndZonesType2 = @Value(uro_large_customer_facility_attribute{0}.uro_large_customer_facility_attribute_uro_districts_and_zones_type{1})
      SET_TO uro_LargeCustomerFacilityAttribute_districtsAndZonesType3 = @Value(uro_large_customer_facility_attribute{0}.uro_large_customer_facility_attribute_uro_districts_and_zones_type{2})
      SET_TO uro_LargeCustomerFacilityAttribute_districtsAndZonesType4 = @Value(uro_large_customer_facility_attribute{0}.uro_large_customer_facility_attribute_uro_districts_and_zones_type{3})
      SET_TO uro_LargeCustomerFacilityAttribute_districtsAndZonesType5 = @Value(uro_large_customer_facility_attribute{0}.uro_large_customer_facility_attribute_uro_districts_and_zones_type{4})
      SET_TO uro_LargeCustomerFacilityAttribute_districtsAndZonesType6 = @Value(uro_large_customer_facility_attribute{0}.uro_large_customer_facility_attribute_uro_districts_and_zones_type{5})
      SET_TO uro_LargeCustomerFacilityAttribute_districtsAndZonesType7 = @Value(uro_large_customer_facility_attribute{0}.uro_large_customer_facility_attribute_uro_districts_and_zones_type{6})
      SET_TO uro_LargeCustomerFacilityAttribute_districtsAndZonesType8 = @Value(uro_large_customer_facility_attribute{0}.uro_large_customer_facility_attribute_uro_districts_and_zones_type{7})
      SET_TO uro_LargeCustomerFacilityAttribute_districtsAndZonesType9 = @Value(uro_large_customer_facility_attribute{0}.uro_large_customer_facility_attribute_uro_districts_and_zones_type{8})
      SET_TO uro_LargeCustomerFacilityAttribute_districtsAndZonesType10 = @Value(uro_large_customer_facility_attribute{0}.uro_large_customer_facility_attribute_uro_districts_and_zones_type{9})
      SET_TO uro_LargeCustomerFacilityAttribute_landUseType = @Value(uro_large_customer_facility_attribute{0}.uro_large_customer_facility_attribute_uro_land_use_type)
      SET_TO uro_LargeCustomerFacilityAttribute_reference = @Value(uro_large_customer_facility_attribute{0}.uro_large_customer_facility_attribute_uro_reference)
      SET_TO uro_LargeCustomerFacilityAttribute_note = @Value(uro_large_customer_facility_attribute{0}.uro_large_customer_facility_attribute_uro_note)
      SET_TO uro_LargeCustomerFacilityAttribute_surveyYear = @Value(uro_large_customer_facility_attribute{0}.uro_large_customer_facility_attribute_uro_survey_year)
      SET_TO uro_BuildingLandSlideRiskAttribute_description1 = @Value(uro_building_disaster_risk_attribute{0}.uro_building_land_slide_risk_attribute_uro_description)
      SET_TO uro_BuildingRiverFloodingRiskAttribute_description = @Value(uro_building_disaster_risk_attribute{0}.uro_building_river_flooding_risk_attribute_uro_description)
      SET_TO uro_BuildingRiverFloodingRiskAttribute_rank = @Value(uro_building_disaster_risk_attribute{0}.uro_building_river_flooding_risk_attribute_uro_rank)
      SET_TO uro_BuildingRiverFloodingRiskAttribute_rankOrg = @Value(uro_building_disaster_risk_attribute{0}.uro_building_river_flooding_risk_attribute_uro_rank_org)
      SET_TO uro_BuildingRiverFloodingRiskAttribute_depth = @Value(uro_building_disaster_risk_attribute{0}.uro_building_river_flooding_risk_attribute_uro_depth)
      SET_TO uro_BuildingRiverFloodingRiskAttribute_adminType = @Value(uro_building_disaster_risk_attribute{0}.uro_building_river_flooding_risk_attribute_uro_admin_type)
      SET_TO uro_BuildingRiverFloodingRiskAttribute_scale = @Value(uro_building_disaster_risk_attribute{0}.uro_building_river_flooding_risk_attribute_uro_scale)
      SET_TO uro_BuildingRiverFloodingRiskAttribute_duration = @Value(uro_building_disaster_risk_attribute{0}.uro_building_river_flooding_risk_attribute_uro_duration)
      SET_TO uro_BuildingTsunamiRiskAttribute_description = @Value(uro_building_disaster_risk_attribute{0}.uro_building_tsunami_risk_attribute_uro_description)
      SET_TO uro_BuildingTsunamiRiskAttribute_rank = @Value(uro_building_disaster_risk_attribute{0}.uro_building_tsunami_risk_attribute_uro_rank)
      SET_TO uro_BuildingTsunamiRiskAttribute_rankOrg = @Value(uro_building_disaster_risk_attribute{0}.uro_building_river_flooding_risk_attribute_uro_rank_org)
      SET_TO uro_BuildingTsunamiRiskAttribute_depth = @Value(uro_building_disaster_risk_attribute{0}.uro_building_tsunami_risk_attribute_uro_depth)
      SET_TO uro_BuildingHighTideRiskAttribute_description = @Value(uro_building_disaster_risk_attribute{0}.uro_building_high_tide_risk_attribute_uro_description)
      SET_TO uro_BuildingHighTideRiskAttribute_rank = @Value(uro_building_disaster_risk_attribute{0}.uro_building_high_tide_risk_attribute_uro_rank)
      SET_TO uro_BuildingHighTideRiskAttribute_rankOrg = @Value(uro_building_disaster_risk_attribute{0}.uro_building_high_tide_risk_attribute_uro_rank_org)
      SET_TO uro_BuildingHighTideRiskAttribute_depth = @Value(uro_building_disaster_risk_attribute{0}.uro_building_high_tide_risk_attribute_uro_depth)
      SET_TO uro_BuildingInlandFloodingRiskAttribute_description = @Value(uro_building_disaster_risk_attribute{0}.uro_building_land_slide_risk_attribute_uro_description)
      SET_TO uro_BuildingInlandFloodingRiskAttribute_rank = @Value(uro_building_disaster_risk_attribute{0}.uro_building_inland_flooding_risk_attribute_uro_rank)
      SET_TO uro_BuildingInlandFloodingRiskAttribute_rankOrg = @Value(uro_building_disaster_risk_attribute{0}.uro_building_river_flooding_risk_attribute_uro_rank_org)
      SET_TO uro_BuildingInlandFloodingRiskAttribute_depth = @Value(uro_building_disaster_risk_attribute{0}.uro_building_inland_flooding_risk_attribute_uro_depth)
      SET_TO uro_BuildingLandSlideRiskAttribute_areaType1 = @Value(uro_building_disaster_risk_attribute{0}.uro_building_land_slide_risk_attribute_uro_area_type)
      SET_TO uro_BuildingLandSlideRiskAttribute_description2 = @Value(uro_building_disaster_risk_attribute{1}.uro_building_land_slide_risk_attribute_uro_description)
      SET_TO uro_BuildingLandSlideRiskAttribute_areaType2 = @Value(uro_building_disaster_risk_attribute{1}.uro_building_land_slide_risk_attribute_uro_area_type)
      SET_TO uro_BuildingLandSlideRiskAttribute_description3 = @Value(uro_building_disaster_risk_attribute{2}.uro_building_land_slide_risk_attribute_uro_description)
      SET_TO uro_BuildingLandSlideRiskAttribute_areaType3 = @Value(uro_building_disaster_risk_attribute{2}.uro_building_land_slide_risk_attribute_uro_area_type)
      SET_TO uro_KeyValuePairAttribute_key1 = @Value(uro_key_value_pair_attribute{0}.uro_key_value_pair_attribute_uro_key)
      SET_TO uro_KeyValuePairAttribute_codeValue1 = @Value(uro_key_value_pair_attribute{0}.uro_key_value_pair_attribute_uro_code_value)
      SET_TO uro_KeyValuePairAttribute_key2 = @Value(uro_key_value_pair_attribute{1}.uro_key_value_pair_attribute_uro_key)
      SET_TO uro_KeyValuePairAttribute_codeValue2 = @Value(uro_key_value_pair_attribute{1}.uro_key_value_pair_attribute_uro_code_value)
      SET_TO uro_KeyValuePairAttribute_key3 = @Value(uro_key_value_pair_attribute{2}.uro_key_value_pair_attribute_uro_key)
      SET_TO uro_KeyValuePairAttribute_codeValue3 = @Value(uro_key_value_pair_attribute{2}.uro_key_value_pair_attribute_uro_code_value)
      SET_TO uro_KeyValuePairAttribute_key4 = @Value(uro_key_value_pair_attribute{3}.uro_key_value_pair_attribute_uro_key)
      SET_TO uro_KeyValuePairAttribute_codeValue4 = @Value(uro_key_value_pair_attribute{3}.uro_key_value_pair_attribute_uro_code_value)
      SET_TO uro_KeyValuePairAttribute_key5 = @Value(uro_key_value_pair_attribute{4}.uro_key_value_pair_attribute_uro_key)
      SET_TO uro_KeyValuePairAttribute_codeValue5 = @Value(uro_key_value_pair_attribute{4}.uro_key_value_pair_attribute_uro_code_value)
      SET_TO uro_KeyValuePairAttribute_key6 = @Value(uro_key_value_pair_attribute{5}.uro_key_value_pair_attribute_uro_key)
      SET_TO uro_KeyValuePairAttribute_codeValue6 = @Value(uro_key_value_pair_attribute{5}.uro_key_value_pair_attribute_uro_code_value)
      SET_TO uro_KeyValuePairAttribute_key7 = @Value(uro_key_value_pair_attribute{6}.uro_key_value_pair_attribute_uro_key)
      SET_TO uro_KeyValuePairAttribute_codeValue7 = @Value(uro_key_value_pair_attribute{6}.uro_key_value_pair_attribute_uro_code_value)
      SET_TO uro_KeyValuePairAttribute_key8 = @Value(uro_key_value_pair_attribute{7}.uro_key_value_pair_attribute_uro_key)
      SET_TO uro_KeyValuePairAttribute_codeValue8 = @Value(uro_key_value_pair_attribute{7}.uro_key_value_pair_attribute_uro_code_value)
      SET_TO uro_KeyValuePairAttribute_key9 = @Value(uro_key_value_pair_attribute{8}.uro_key_value_pair_attribute_uro_key)
      SET_TO uro_KeyValuePairAttribute_codeValue9 = @Value(uro_key_value_pair_attribute{8}.uro_key_value_pair_attribute_uro_code_value)
      SET_TO uro_KeyValuePairAttribute_key10 = @Value(uro_key_value_pair_attribute{9}.uro_key_value_pair_attribute_uro_key)
      SET_TO uro_KeyValuePairAttribute_codeValue10 = @Value(uro_key_value_pair_attribute{9}.uro_key_value_pair_attribute_uro_code_value)
      SET_TO uro_BuildingDataQualityAttribute_srcScale1 = @Value(uro_building_data_quality_attribute{0}.uro_building_data_quality_attribute_uro_src_scale{0})
      SET_TO uro_BuildingDataQualityAttribute_srcScale2 = @Value(uro_building_data_quality_attribute{0}.uro_building_data_quality_attribute_uro_src_scale{1})
      SET_TO uro_BuildingDataQualityAttribute_srcScale3 = @Value(uro_building_data_quality_attribute{0}.uro_building_data_quality_attribute_uro_src_scale{2})
      SET_TO uro_BuildingDataQualityAttribute_srcScale4 = @Value(uro_building_data_quality_attribute{0}.uro_building_data_quality_attribute_uro_src_scale{3})
      SET_TO uro_BuildingDataQualityAttribute_srcScale5 = @Value(uro_building_data_quality_attribute{0}.uro_building_data_quality_attribute_uro_src_scale{4})
      SET_TO uro_BuildingDataQualityAttribute_srcScale6 = @Value(uro_building_data_quality_attribute{0}.uro_building_data_quality_attribute_uro_src_scale{5})
      SET_TO uro_BuildingDataQualityAttribute_srcScale7 = @Value(uro_building_data_quality_attribute{0}.uro_building_data_quality_attribute_uro_src_scale{6})
      SET_TO uro_BuildingDataQualityAttribute_srcScale8 = @Value(uro_building_data_quality_attribute{0}.uro_building_data_quality_attribute_uro_src_scale{7})
      SET_TO uro_BuildingDataQualityAttribute_srcScale9 = @Value(uro_building_data_quality_attribute{0}.uro_building_data_quality_attribute_uro_src_scale{8})
      SET_TO uro_BuildingDataQualityAttribute_srcScale10 = @Value(uro_building_data_quality_attribute{0}.uro_building_data_quality_attribute_uro_src_scale{9})
      SET_TO uro_BuildingDataQualityAttribute_geometrySrcDesc1 = @Value(uro_building_data_quality_attribute{0}.uro_building_data_quality_attribute_uro_geometry_src_desc{0})
      SET_TO uro_BuildingDataQualityAttribute_geometrySrcDesc2 = @Value(uro_building_data_quality_attribute{0}.uro_building_data_quality_attribute_uro_geometry_src_desc{1})
      SET_TO uro_BuildingDataQualityAttribute_geometrySrcDesc3 = @Value(uro_building_data_quality_attribute{0}.uro_building_data_quality_attribute_uro_geometry_src_desc{2})
      SET_TO uro_BuildingDataQualityAttribute_geometrySrcDesc4 = @Value(uro_building_data_quality_attribute{0}.uro_building_data_quality_attribute_uro_geometry_src_desc{3})
      SET_TO uro_BuildingDataQualityAttribute_geometrySrcDesc5 = @Value(uro_building_data_quality_attribute{0}.uro_building_data_quality_attribute_uro_geometry_src_desc{4})
      SET_TO uro_BuildingDataQualityAttribute_geometrySrcDesc6 = @Value(uro_building_data_quality_attribute{0}.uro_building_data_quality_attribute_uro_geometry_src_desc{5})
      SET_TO uro_BuildingDataQualityAttribute_geometrySrcDesc7 = @Value(uro_building_data_quality_attribute{0}.uro_building_data_quality_attribute_uro_geometry_src_desc{6})
      SET_TO uro_BuildingDataQualityAttribute_geometrySrcDesc8 = @Value(uro_building_data_quality_attribute{0}.uro_building_data_quality_attribute_uro_geometry_src_desc{7})
      SET_TO uro_BuildingDataQualityAttribute_geometrySrcDesc9 = @Value(uro_building_data_quality_attribute{0}.uro_building_data_quality_attribute_uro_geometry_src_desc{8})
      SET_TO uro_BuildingDataQualityAttribute_geometrySrcDesc10 = @Value(uro_building_data_quality_attribute{0}.uro_building_data_quality_attribute_uro_geometry_src_desc{9})
      SET_TO uro_BuildingDataQualityAttribute_thematicSrcDesc1 = @Value(uro_building_data_quality_attribute{0}.uro_building_data_quality_attribute_uro_thematic_src_desc{0})
      SET_TO uro_BuildingDataQualityAttribute_thematicSrcDesc2 = @Value(uro_building_data_quality_attribute{0}.uro_building_data_quality_attribute_uro_thematic_src_desc{1})
      SET_TO uro_BuildingDataQualityAttribute_thematicSrcDesc3 = @Value(uro_building_data_quality_attribute{0}.uro_building_data_quality_attribute_uro_thematic_src_desc{2})
      SET_TO uro_BuildingDataQualityAttribute_thematicSrcDesc4 = @Value(uro_building_data_quality_attribute{0}.uro_building_data_quality_attribute_uro_thematic_src_desc{3})
      SET_TO uro_BuildingDataQualityAttribute_thematicSrcDesc5 = @Value(uro_building_data_quality_attribute{0}.uro_building_data_quality_attribute_uro_thematic_src_desc{4})
      SET_TO uro_BuildingDataQualityAttribute_thematicSrcDesc6 = @Value(uro_building_data_quality_attribute{0}.uro_building_data_quality_attribute_uro_thematic_src_desc{5})
      SET_TO uro_BuildingDataQualityAttribute_thematicSrcDesc7 = @Value(uro_building_data_quality_attribute{0}.uro_building_data_quality_attribute_uro_thematic_src_desc{6})
      SET_TO uro_BuildingDataQualityAttribute_thematicSrcDesc8 = @Value(uro_building_data_quality_attribute{0}.uro_building_data_quality_attribute_uro_thematic_src_desc{7})
      SET_TO uro_BuildingDataQualityAttribute_thematicSrcDesc9 = @Value(uro_building_data_quality_attribute{0}.uro_building_data_quality_attribute_uro_thematic_src_desc{8})
      SET_TO uro_BuildingDataQualityAttribute_thematicSrcDesc10 = @Value(uro_building_data_quality_attribute{0}.uro_building_data_quality_attribute_uro_thematic_src_desc{9})
      SET_TO uro_BuildingDataQualityAttribute_appearanceSrcDesc1 = @Value(uro_building_data_quality_attribute{0}.uro_building_data_quality_attribute_uro_appearance_src_desc{0})
      SET_TO uro_BuildingDataQualityAttribute_appearanceSrcDesc2 = @Value(uro_building_data_quality_attribute{0}.uro_building_data_quality_attribute_uro_appearance_src_desc{1})
      SET_TO uro_BuildingDataQualityAttribute_appearanceSrcDesc3 = @Value(uro_building_data_quality_attribute{0}.uro_building_data_quality_attribute_uro_appearance_src_desc{2})
      SET_TO uro_BuildingDataQualityAttribute_appearanceSrcDesc4 = @Value(uro_building_data_quality_attribute{0}.uro_building_data_quality_attribute_uro_appearance_src_desc{3})
      SET_TO uro_BuildingDataQualityAttribute_appearanceSrcDesc5 = @Value(uro_building_data_quality_attribute{0}.uro_building_data_quality_attribute_uro_appearance_src_desc{4})
      SET_TO uro_BuildingDataQualityAttribute_appearanceSrcDesc6 = @Value(uro_building_data_quality_attribute{0}.uro_building_data_quality_attribute_uro_appearance_src_desc{5})
      SET_TO uro_BuildingDataQualityAttribute_appearanceSrcDesc7 = @Value(uro_building_data_quality_attribute{0}.uro_building_data_quality_attribute_uro_appearance_src_desc{6})
      SET_TO uro_BuildingDataQualityAttribute_appearanceSrcDesc8 = @Value(uro_building_data_quality_attribute{0}.uro_building_data_quality_attribute_uro_appearance_src_desc{7})
      SET_TO uro_BuildingDataQualityAttribute_appearanceSrcDesc9 = @Value(uro_building_data_quality_attribute{0}.uro_building_data_quality_attribute_uro_appearance_src_desc{8})
      SET_TO uro_BuildingDataQualityAttribute_appearanceSrcDesc10 = @Value(uro_building_data_quality_attribute{0}.uro_building_data_quality_attribute_uro_appearance_src_desc{9})
      SET_TO uro_BuildingDataQualityAttribute_lod1HeightType = @Value(uro_building_data_quality_attribute{0}.uro_building_data_quality_attribute_uro_lod1_height_type)
      SET_TO uro_BuildingDataQualityAttribute_lodType1 = @Value(uro_building_data_quality_attribute{0}.uro_building_data_quality_attribute_uro_lod_type{0})
      SET_TO uro_BuildingDataQualityAttribute_lodType2 = @Value(uro_building_data_quality_attribute{0}.uro_building_data_quality_attribute_uro_lod_type{1})
      SET_TO uro_BuildingDataQualityAttribute_lodType3 = @Value(uro_building_data_quality_attribute{0}.uro_building_data_quality_attribute_uro_lod_type{2})
      SET_TO uro_buildingIDAttribute = @Value(gml_id)
    -> AttributeManager_Building
AttributeManager_Building
    ATTR_TABLE:
      RENAME_SET_VALUE gml_id > bldg_Building_gml_id
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      RENAME_SET_VALUE citygml_class > bldg_class
      REMOVE citygml_class_codeSpace
      REMOVE citygml_function{}
      REMOVE citygml_function{}.codeSpace
      REMOVE citygml_usage{}
      REMOVE citygml_usage{}.codeSpace
      RENAME_SET_VALUE citygml_year_of_construction > bldg_yearOfConstruction
      RENAME_SET_VALUE citygml_year_of_demolition > bldg_yearOfDemolition
      RENAME_SET_VALUE citygml_roof_type > bldg_roofType
      REMOVE citygml_roof_type_codeSpace
      RENAME_SET_VALUE citygml_measured_height > bldg_measuredHeight
      REMOVE citygml_measured_height_units
      RENAME_SET_VALUE citygml_storeys_above_ground > bldg_storeysAboveGround
      RENAME_SET_VALUE citygml_storeys_below_ground > bldg_storeysBelowGround
      RENAME_SET_VALUE citygml_storey_heights_above_ground > bldg_storeyHeightsAboveGround
      REMOVE citygml_storey_heights_above_ground_units
      RENAME_SET_VALUE citygml_storey_heights_below_ground > bldg_storeyHeightsBelowGround
      REMOVE citygml_storey_heights_below_ground_units
      REMOVE citygml_outer_building_installation{}.xlink_href
      REMOVE citygml_interior_building_installation{}.xlink_href
      REMOVE citygml_bounded_by{}.xlink_href
      REMOVE citygml_level_of_detail{}
      REMOVE citygml_interior_room{}.xlink_href
      REMOVE citygml_consists_of_building_part{}.xlink_href
      REMOVE citygml_address{}.xlink_href
      REMOVE uro_building_data_quality_attribute{}.uro_building_data_quality_attribute_uro_src_scale{}
      REMOVE uro_building_data_quality_attribute{}.uro_building_data_quality_attribute_uro_src_scale{}.codeSpace
      REMOVE uro_building_data_quality_attribute{}.uro_building_data_quality_attribute_uro_geometry_src_desc{}
      REMOVE uro_building_data_quality_attribute{}.uro_building_data_quality_attribute_uro_geometry_src_desc{}.codeSpace
      REMOVE uro_building_data_quality_attribute{}.uro_building_data_quality_attribute_uro_thematic_src_desc{}
      REMOVE uro_building_data_quality_attribute{}.uro_building_data_quality_attribute_uro_thematic_src_desc{}.codeSpace
      REMOVE uro_building_data_quality_attribute{}.uro_building_data_quality_attribute_uro_appearance_src_desc{}
      REMOVE uro_building_data_quality_attribute{}.uro_building_data_quality_attribute_uro_appearance_src_desc{}.codeSpace
      REMOVE uro_building_data_quality_attribute{}.uro_building_data_quality_attribute_uro_lod1_height_type
      REMOVE uro_building_data_quality_attribute{}.uro_building_data_quality_attribute_uro_lod1_height_type_codeSpace
      REMOVE uro_building_data_quality_attribute{}.uro_building_data_quality_attribute_uro_lod_type{}
      REMOVE uro_building_detail_attribute{}.uro_building_detail_attribute_uro_serial_number_of_building_certification
      REMOVE uro_building_detail_attribute{}.uro_building_detail_attribute_uro_site_area
      REMOVE uro_building_detail_attribute{}.uro_building_detail_attribute_uro_site_area_units
      REMOVE uro_building_detail_attribute{}.uro_building_detail_attribute_uro_total_floor_area
      REMOVE uro_building_detail_attribute{}.uro_building_detail_attribute_uro_total_floor_area_units
      REMOVE uro_building_detail_attribute{}.uro_building_detail_attribute_uro_building_footprint_area
      REMOVE uro_building_detail_attribute{}.uro_building_detail_attribute_uro_building_footprint_area_units
      REMOVE uro_building_detail_attribute{}.uro_building_detail_attribute_uro_building_roof_edge_area
      REMOVE uro_building_detail_attribute{}.uro_building_detail_attribute_uro_building_roof_edge_area_units
      REMOVE uro_building_detail_attribute{}.uro_building_detail_attribute_uro_development_area
      REMOVE uro_building_detail_attribute{}.uro_building_detail_attribute_uro_development_area_units
      REMOVE uro_building_detail_attribute{}.uro_building_detail_attribute_uro_building_structure_type
      REMOVE uro_building_detail_attribute{}.uro_building_detail_attribute_uro_building_structure_type_codeSpace
      REMOVE uro_building_detail_attribute{}.uro_building_detail_attribute_uro_building_structure_org_type
      REMOVE uro_building_detail_attribute{}.uro_building_detail_attribute_uro_building_structure_org_type_codeSpace
      REMOVE uro_building_detail_attribute{}.uro_building_detail_attribute_uro_fireproof_structure_type
      REMOVE uro_building_detail_attribute{}.uro_building_detail_attribute_uro_fireproof_structure_type_codeSpace
      REMOVE uro_building_detail_attribute{}.uro_building_detail_attribute_uro_implementing_body
      REMOVE uro_building_detail_attribute{}.uro_building_detail_attribute_uro_urban_plan_type
      REMOVE uro_building_detail_attribute{}.uro_building_detail_attribute_uro_urban_plan_type_codeSpace
      REMOVE uro_building_detail_attribute{}.uro_building_detail_attribute_uro_area_classification_type
      REMOVE uro_building_detail_attribute{}.uro_building_detail_attribute_uro_area_classification_type_codeSpace
      REMOVE uro_building_detail_attribute{}.uro_building_detail_attribute_uro_districts_and_zones_type{}
      REMOVE uro_building_detail_attribute{}.uro_building_detail_attribute_uro_districts_and_zones_type{}.codeSpace
      REMOVE uro_building_detail_attribute{}.uro_building_detail_attribute_uro_land_use_type
      REMOVE uro_building_detail_attribute{}.uro_building_detail_attribute_uro_land_use_type_codeSpace
      REMOVE uro_building_detail_attribute{}.uro_building_detail_attribute_uro_reference
      REMOVE uro_building_detail_attribute{}.uro_building_detail_attribute_uro_major_usage
      REMOVE uro_building_detail_attribute{}.uro_building_detail_attribute_uro_major_usage_codeSpace
      REMOVE uro_building_detail_attribute{}.uro_building_detail_attribute_uro_major_usage2
      REMOVE uro_building_detail_attribute{}.uro_building_detail_attribute_uro_major_usage2_codeSpace
      REMOVE uro_building_detail_attribute{}.uro_building_detail_attribute_uro_org_usage
      REMOVE uro_building_detail_attribute{}.uro_building_detail_attribute_uro_org_usage_codeSpace
      REMOVE uro_building_detail_attribute{}.uro_building_detail_attribute_uro_org_usage2
      REMOVE uro_building_detail_attribute{}.uro_building_detail_attribute_uro_org_usage2_codeSpace
      REMOVE uro_building_detail_attribute{}.uro_building_detail_attribute_uro_detailed_usage
      REMOVE uro_building_detail_attribute{}.uro_building_detail_attribute_uro_detailed_usage_codeSpace
      REMOVE uro_building_detail_attribute{}.uro_building_detail_attribute_uro_detailed_usage2
      REMOVE uro_building_detail_attribute{}.uro_building_detail_attribute_uro_detailed_usage2_codeSpace
      REMOVE uro_building_detail_attribute{}.uro_building_detail_attribute_uro_detailed_usage3
      REMOVE uro_building_detail_attribute{}.uro_building_detail_attribute_uro_detailed_usage3_codeSpace
      REMOVE uro_building_detail_attribute{}.uro_building_detail_attribute_uro_ground_floor_usage
      REMOVE uro_building_detail_attribute{}.uro_building_detail_attribute_uro_ground_floor_usage_codeSpace
      REMOVE uro_building_detail_attribute{}.uro_building_detail_attribute_uro_second_floor_usage
      REMOVE uro_building_detail_attribute{}.uro_building_detail_attribute_uro_second_floor_usage_codeSpace
      REMOVE uro_building_detail_attribute{}.uro_building_detail_attribute_uro_third_floor_usage
      REMOVE uro_building_detail_attribute{}.uro_building_detail_attribute_uro_third_floor_usage_codeSpace
      REMOVE uro_building_detail_attribute{}.uro_building_detail_attribute_uro_basement_usage
      REMOVE uro_building_detail_attribute{}.uro_building_detail_attribute_uro_basement_usage_codeSpace
      REMOVE uro_building_detail_attribute{}.uro_building_detail_attribute_uro_basement_first_usage
      REMOVE uro_building_detail_attribute{}.uro_building_detail_attribute_uro_basement_first_usage_codeSpace
      REMOVE uro_building_detail_attribute{}.uro_building_detail_attribute_uro_basement_second_usage
      REMOVE uro_building_detail_attribute{}.uro_building_detail_attribute_uro_basement_second_usage_codeSpace
      REMOVE uro_building_detail_attribute{}.uro_building_detail_attribute_uro_vacancy
      REMOVE uro_building_detail_attribute{}.uro_building_detail_attribute_uro_vacancy_codeSpace
      REMOVE uro_building_detail_attribute{}.uro_building_detail_attribute_uro_building_coverage_rate
      REMOVE uro_building_detail_attribute{}.uro_building_detail_attribute_uro_floor_area_rate
      REMOVE uro_building_detail_attribute{}.uro_building_detail_attribute_uro_specified_building_coverage_rate
      REMOVE uro_building_detail_attribute{}.uro_building_detail_attribute_uro_specified_floor_area_rate
      REMOVE uro_building_detail_attribute{}.uro_building_detail_attribute_uro_standard_floor_area_rate
      REMOVE uro_building_detail_attribute{}.uro_building_detail_attribute_uro_building_height
      REMOVE uro_building_detail_attribute{}.uro_building_detail_attribute_uro_building_height_units
      REMOVE uro_building_detail_attribute{}.uro_building_detail_attribute_uro_eave_height
      REMOVE uro_building_detail_attribute{}.uro_building_detail_attribute_uro_eave_height_units
      REMOVE uro_building_detail_attribute{}.uro_building_detail_attribute_uro_note
      REMOVE uro_building_detail_attribute{}.uro_building_detail_attribute_uro_survey_year
      REMOVE uro_building_disaster_risk_attribute{}.uro_building_high_tide_risk_attribute_uro_description
      REMOVE uro_building_disaster_risk_attribute{}.uro_building_high_tide_risk_attribute_uro_description_codeSpace
      REMOVE uro_building_disaster_risk_attribute{}.uro_building_high_tide_risk_attribute_uro_rank
      REMOVE uro_building_disaster_risk_attribute{}.uro_building_high_tide_risk_attribute_uro_rank_codeSpace
      REMOVE uro_building_disaster_risk_attribute{}.uro_building_high_tide_risk_attribute_uro_rank_org
      REMOVE uro_building_disaster_risk_attribute{}.uro_building_high_tide_risk_attribute_uro_rank_org_codeSpace
      REMOVE uro_building_disaster_risk_attribute{}.uro_building_high_tide_risk_attribute_uro_depth
      REMOVE uro_building_disaster_risk_attribute{}.uro_building_high_tide_risk_attribute_uro_depth_units
      REMOVE uro_building_disaster_risk_attribute{}.uro_building_inland_flooding_risk_attribute_uro_description
      REMOVE uro_building_disaster_risk_attribute{}.uro_building_inland_flooding_risk_attribute_uro_description_codeSpace
      REMOVE uro_building_disaster_risk_attribute{}.uro_building_inland_flooding_risk_attribute_uro_rank
      REMOVE uro_building_disaster_risk_attribute{}.uro_building_inland_flooding_risk_attribute_uro_rank_codeSpace
      REMOVE uro_building_disaster_risk_attribute{}.uro_building_inland_flooding_risk_attribute_uro_rank_org
      REMOVE uro_building_disaster_risk_attribute{}.uro_building_inland_flooding_risk_attribute_uro_rank_org_codeSpace
      REMOVE uro_building_disaster_risk_attribute{}.uro_building_inland_flooding_risk_attribute_uro_depth
      REMOVE uro_building_disaster_risk_attribute{}.uro_building_inland_flooding_risk_attribute_uro_depth_units
      REMOVE uro_building_disaster_risk_attribute{}.uro_building_land_slide_risk_attribute_uro_description
      REMOVE uro_building_disaster_risk_attribute{}.uro_building_land_slide_risk_attribute_uro_description_codeSpace
      REMOVE uro_building_disaster_risk_attribute{}.uro_building_land_slide_risk_attribute_uro_area_type
      REMOVE uro_building_disaster_risk_attribute{}.uro_building_land_slide_risk_attribute_uro_area_type_codeSpace
      REMOVE uro_building_disaster_risk_attribute{}.uro_building_river_flooding_risk_attribute_uro_description
      REMOVE uro_building_disaster_risk_attribute{}.uro_building_river_flooding_risk_attribute_uro_description_codeSpace
      REMOVE uro_building_disaster_risk_attribute{}.uro_building_river_flooding_risk_attribute_uro_rank
      REMOVE uro_building_disaster_risk_attribute{}.uro_building_river_flooding_risk_attribute_uro_rank_codeSpace
      REMOVE uro_building_disaster_risk_attribute{}.uro_building_river_flooding_risk_attribute_uro_rank_org
      REMOVE uro_building_disaster_risk_attribute{}.uro_building_river_flooding_risk_attribute_uro_rank_org_codeSpace
      REMOVE uro_building_disaster_risk_attribute{}.uro_building_river_flooding_risk_attribute_uro_depth
      REMOVE uro_building_disaster_risk_attribute{}.uro_building_river_flooding_risk_attribute_uro_depth_units
      REMOVE uro_building_disaster_risk_attribute{}.uro_building_river_flooding_risk_attribute_uro_admin_type
      REMOVE uro_building_disaster_risk_attribute{}.uro_building_river_flooding_risk_attribute_uro_admin_type_codeSpace
      REMOVE uro_building_disaster_risk_attribute{}.uro_building_river_flooding_risk_attribute_uro_scale
      REMOVE uro_building_disaster_risk_attribute{}.uro_building_river_flooding_risk_attribute_uro_scale_codeSpace
      REMOVE uro_building_disaster_risk_attribute{}.uro_building_river_flooding_risk_attribute_uro_duration
      REMOVE uro_building_disaster_risk_attribute{}.uro_building_river_flooding_risk_attribute_uro_duration_units
      REMOVE uro_building_disaster_risk_attribute{}.uro_building_tsunami_risk_attribute_uro_description
      REMOVE uro_building_disaster_risk_attribute{}.uro_building_tsunami_risk_attribute_uro_description_codeSpace
      REMOVE uro_building_disaster_risk_attribute{}.uro_building_tsunami_risk_attribute_uro_rank
      REMOVE uro_building_disaster_risk_attribute{}.uro_building_tsunami_risk_attribute_uro_rank_codeSpace
      REMOVE uro_building_disaster_risk_attribute{}.uro_building_tsunami_risk_attribute_uro_rank_org
      REMOVE uro_building_disaster_risk_attribute{}.uro_building_tsunami_risk_attribute_uro_rank_org_codeSpace
      REMOVE uro_building_disaster_risk_attribute{}.uro_building_tsunami_risk_attribute_uro_depth
      REMOVE uro_building_disaster_risk_attribute{}.uro_building_tsunami_risk_attribute_uro_depth_units
      REMOVE uro_building_idattribute{}.uro_building_idattribute_uro_building_id
      REMOVE uro_building_idattribute{}.uro_building_idattribute_uro_branch_id
      REMOVE uro_building_idattribute{}.uro_building_idattribute_uro_part_id
      REMOVE uro_building_idattribute{}.uro_building_idattribute_uro_prefecture
      REMOVE uro_building_idattribute{}.uro_building_idattribute_uro_prefecture_codeSpace
      REMOVE uro_building_idattribute{}.uro_building_idattribute_uro_city
      REMOVE uro_building_idattribute{}.uro_building_idattribute_uro_city_codeSpace
      REMOVE uro_key_value_pair_attribute{}.uro_key_value_pair_attribute_uro_key
      REMOVE uro_key_value_pair_attribute{}.uro_key_value_pair_attribute_uro_key_codeSpace
      REMOVE uro_key_value_pair_attribute{}.uro_key_value_pair_attribute_uro_code_value
      REMOVE uro_key_value_pair_attribute{}.uro_key_value_pair_attribute_uro_code_value_codeSpace
      REMOVE uro_key_value_pair_attribute{}.uro_key_value_pair_attribute_uro_string_value
      REMOVE uro_key_value_pair_attribute{}.uro_key_value_pair_attribute_uro_int_value
      REMOVE uro_key_value_pair_attribute{}.uro_key_value_pair_attribute_uro_double_value
      REMOVE uro_key_value_pair_attribute{}.uro_key_value_pair_attribute_uro_measured_value
      REMOVE uro_key_value_pair_attribute{}.uro_key_value_pair_attribute_uro_measured_value_units
      REMOVE uro_key_value_pair_attribute{}.uro_key_value_pair_attribute_uro_date_value
      REMOVE uro_key_value_pair_attribute{}.uro_key_value_pair_attribute_uro_uri_value
      REMOVE uro_large_customer_facility_attribute{}.uro_large_customer_facility_attribute_uro_class
      REMOVE uro_large_customer_facility_attribute{}.uro_large_customer_facility_attribute_uro_class_codeSpace
      REMOVE uro_large_customer_facility_attribute{}.uro_large_customer_facility_attribute_uro_name
      REMOVE uro_large_customer_facility_attribute{}.uro_large_customer_facility_attribute_uro_capacity
      REMOVE uro_large_customer_facility_attribute{}.uro_large_customer_facility_attribute_uro_owner
      REMOVE uro_large_customer_facility_attribute{}.uro_large_customer_facility_attribute_uro_total_floor_area
      REMOVE uro_large_customer_facility_attribute{}.uro_large_customer_facility_attribute_uro_total_floor_area_units
      REMOVE uro_large_customer_facility_attribute{}.uro_large_customer_facility_attribute_uro_total_store_floor_area
      REMOVE uro_large_customer_facility_attribute{}.uro_large_customer_facility_attribute_uro_total_store_floor_area_units
      REMOVE uro_large_customer_facility_attribute{}.uro_large_customer_facility_attribute_uro_inaugural_date
      REMOVE uro_large_customer_facility_attribute{}.uro_large_customer_facility_attribute_uro_key_tenants
      REMOVE uro_large_customer_facility_attribute{}.uro_large_customer_facility_attribute_uro_availability
      REMOVE uro_large_customer_facility_attribute{}.uro_large_customer_facility_attribute_uro_urban_plan_type
      REMOVE uro_large_customer_facility_attribute{}.uro_large_customer_facility_attribute_uro_urban_plan_type_codeSpace
      REMOVE uro_large_customer_facility_attribute{}.uro_large_customer_facility_attribute_uro_area_classification_type
      REMOVE uro_large_customer_facility_attribute{}.uro_large_customer_facility_attribute_uro_area_classification_type_codeSpace
      REMOVE uro_large_customer_facility_attribute{}.uro_large_customer_facility_attribute_uro_districts_and_zones_type{}
      REMOVE uro_large_customer_facility_attribute{}.uro_large_customer_facility_attribute_uro_districts_and_zones_type{}.codeSpace
      REMOVE uro_large_customer_facility_attribute{}.uro_large_customer_facility_attribute_uro_land_use_type
      REMOVE uro_large_customer_facility_attribute{}.uro_large_customer_facility_attribute_uro_land_use_type_codeSpace
      REMOVE uro_large_customer_facility_attribute{}.uro_large_customer_facility_attribute_uro_reference
      REMOVE uro_large_customer_facility_attribute{}.uro_large_customer_facility_attribute_uro_note
      REMOVE uro_large_customer_facility_attribute{}.uro_large_customer_facility_attribute_uro_survey_year
      REMOVE Attribute
      REMOVE citygml_address
      RENAME_SET_VALUE Address > bldg_address
    USER_EXPOSED_ATTRIBUTES = Definition.id,uro_BuildingDisasterRiskAttribute_areaType3,uro_BuildingDisasterRiskAttribute_description1
    -> FeatureJoiner_Building_2 [LEFT]
Sampler
    RATE = 1
    SAMPLE_MODE = No
    SAMPLE_TYPE_LONG = First N Features
    SAMPLED -> XMLTemplater [ROOT]
    SAMPLED -> XMLTemplater [SUB]
    NOT_SAMPLED -> XMLTemplater [SUB]
XMLTemplater
    OUTPUT_XML_HEADER = Yes
    RESULT_ATTRIBUTE = _result
    ROOT_QUERY_EXPR:
      <root>{
          fme:process-features("SUB")
      }</root>
    SUB_QUERY_EXPR:
      declare namespace gml="http://www.opengis.net/gml";
      declare namespace gen="http://www.opengis.net/citygml/generics/2.0";
      declare namespace bldg="http://www.opengis.net/citygml/building/2.0";

      {
      let $doc := fme:get-xml-attribute("text_line_data")
      for $b in $doc//bldg:Building
      return
      <Building gml_id="{data($b/@gml:id)}">{
          for $genStrAttr in $b/gen:stringAttribute
          where $b/gen:stringAttribute
              let $tempgenstrname := "gen_"||{data($genStrAttr/@name)}
              let $genstrname := fn:translate($tempgenstrname, "・（(- 「」、。－+＋）)", "____________")
              let $genstrtype := "TEXT"
              return
              <attr name="{$genstrname}" type="{$genstrtype}">{data($genStrAttr/gen:value)}</attr>
          }{
          for $genIntAttr in $b/gen:intAttribute
          where $b/gen:intAttribute
              let $tempgenintname := "gen_"||{data($genIntAttr/@name)}
              let $genintname := fn:translate($tempgenintname, "・（(- 「」、。－+＋）)", "____________")
              let $geninttype := "LONG"
              return
              <attr name="{$genintname}" type="{$geninttype}">{data($genIntAttr/gen:value)}</attr>
          }{
          for $genDoubleAttr in $b/gen:doubleAttribute
          where $b/gen:doubleAttribute
              let $tempgendoublename := "gen_"||{data($genDoubleAttr/@name)}
              let $gendoublename := fn:translate($tempgendoublename, "・（(- 「」、。－+＋）)", "____________")
              let $gendoubletype := "DOUBLE"
              return
              <attr name="{$gendoublename}" type="{$gendoubletype}">{data($genDoubleAttr/gen:value)}</attr>
          }{
          for $genDateAttr in $b/gen:dateAttribute
          where $b/gen:dateAttribute
              let $tempgendatename := "gen_"||{data($genDateAttr/@name)}
              let $gendatename := fn:translate($tempgendatename, "・（(- 「」、。－+＋）)", "____________")
              let $gendatetype := "TEXT"
              return
              <attr name="{$gendatename}" type="{$gendatetype}">{data($genDateAttr/gen:value)}</attr>
          }{
          for $genUriAttr in $b/gen:uriAttribute
          where $b/gen:uriAttribute
              let $tempgenuriname := "gen_"||{data($genUriAttr/@name)}
              let $genuriname := fn:translate($tempgenuriname, "・（(- 「」、。－+＋）)", "____________")
              let $genuritype := "TEXT"
              return
              <attr name="{$genuriname}" type="{$genuritype}">{data($genUriAttr/gen:value)}</attr>
          }{
          for $genMeasureAttr in $b/gen:measureAttribute
          where $b/gen:measureAttribute
              let $tempgenmeasurename := "gen_"||{data($genMeasureAttr/@name)}
              let $genmeasurename := fn:translate($tempgenmeasurename, "・（(- 「」、。－+＋）)", "____________")
              let $genmeasuretype := "DOUBLE"
              return
              <attr name="{$genmeasurename}" type="{$genmeasuretype}">{data($genMeasureAttr/gen:value)}</attr>
          }{
          for $attrSet in $b/gen:genericAttributeSet
          where $attrSet/gen:measureAttribute
              for $measureAttr in $attrSet/gen:measureAttribute
              let $mtempname := "gen_"||{data($attrSet/@name)}||"_"||{data($measureAttr/@name)}
              let $mname := fn:translate($mtempname, "・（(- 「」、。－+＋）)", "____________")
              let $mtype := "DOUBLE"
              return
              <attr name="{$mname}" type="{$mtype}">{data($measureAttr/gen:value)}</attr>
          }{
          for $attrSet in $b/gen:genericAttributeSet
          where $attrSet/gen:intAttribute
              for $intAttr in $attrSet/gen:intAttribute
              let $itempname := "gen_"||{data($attrSet/@name)}||"_"||{data($intAttr/@name)}
              let $iname := fn:translate($itempname, "・（(- 「」、。－+＋）)", "____________")
              let $itype := "LONG"
              return
              <attr name="{$iname}" type="{$itype}">{data($intAttr/gen:value)}</attr>
          }{
          for $attrSet in $b/gen:genericAttributeSet
          where $attrSet/gen:stringAttribute
              for $stringAttr in $attrSet/gen:stringAttribute
              let $stempname := "gen_"||{data($attrSet/@name)}||"_"||{data($stringAttr/@name)}
              let $sname := fn:translate($stempname, "・（(- 「」、。－+＋）)", "____________")
              let $stype := "TEXT"
              return
              <attr name="{$sname}" type="{$stype}">{data($stringAttr/gen:value)}</attr>
          }{
          for $attrSet in $b/gen:genericAttributeSet
          where $attrSet/gen:doubleAttribute
              for $doubleAttr in $attrSet/gen:doubleAttribute
              let $dtempname := "gen_"||{data($attrSet/@name)}||"_"||{data($doubleAttr/@name)}
              let $dname := fn:translate($dtempname, "・（(- 「」、。－+＋）)", "____________")
              let $dtype := "DOUBLE"
              return
              <attr name="{$dname}" type="{$dtype}">{data($doubleAttr/gen:value)}</attr>
          }{
          for $attrSet in $b/gen:genericAttributeSet
          where $attrSet/gen:dateAttribute
              for $dateAttr in $attrSet/gen:dateAttribute
              let $datetempname := "gen_"||{data($attrSet/@name)}||"_"||{data($dateAttr/@name)}
              let $datename := fn:translate($datetempname, "・（(- 「」、。－+＋）)", "____________")
              let $datetype := "TEXT"
              return
              <attr name="{$datename}" type="{$datetype}">{data($dateAttr/gen:value)}</attr>
          }{
          for $attrSet in $b/gen:genericAttributeSet
          where $attrSet/gen:uriAttribute
              for $uriAttr in $attrSet/gen:uriAttribute
              let $utempname := "gen_"||{data($attrSet/@name)}||"_"||{data($uriAttr/@name)}
              let $uname := fn:translate($utempname, "・（(- 「」、。－+＋）)", "____________")
              let $utype := "TEXT"
              return
              <attr name="{$uname}" type="{$utype}">{data($uriAttr/gen:value)}</attr>
          }</Building>
      }
    VISIBLE_QUERY_VALIDATE = Yes
    -> TextDecoder
TextDecoder
    DEST_ATTR = _decoded
    ENCODING_TYPE = XML
    STRING_TO_DECODE = @Value(_result)
    -> XMLFormatter
XMLFormatter
    COLLAPSE_EMPTY_ELEMENT = No
    FORMATTING_CHOICE = Pretty-Print XML
    INDENT_SIZE = 1
    LIST_NAME = _xml_error
    NAMESPACE_CLEANUP = No
    OUTPUT_ENCODING = utf-8
    REMOVE_ALL_COMMENT = No
    REMOVE_EMPTY_ELEMENT = No
    REMOVE_XML_HEADER = no
    REPLACE_TABS_WITH_SPACES = no
    SCHEMALOC_CLEANUP = No
    TEXT_INDENT = no
    WHITESPACE_HANDLING = Preserve all whitespace
    XML_ATTR_TEXT = _decoded
    XML_INPUT_TYPE = Attribute Specifying XML Text
    XML_OUTPUT_ATTR = _result
    XML_OUTPUT_TYPE = Attribute
    PASSED -> AttributeKeeper
AttributeKeeper
    CREATE_BULK_MODE_FEATURES = NO
    KEEP_ATTRS = _result
    -> XMLFragmenter
XMLFragmenter
    ATTRIBUTE_XML = _result
    EMBEDDED_EXPRESSIONS = root/Building
    FEATURE_TYPES_FORMAT_NAME = XML
    MERGE_ATTRS = No
    REJECT_FEATURES_WITH_NO_FRAGMENTS = YES
    XML_SOURCE_TYPE = Attribute with XML document
    FRAGMENTS -> XMLXQueryExtractor
XMLXQueryExtractor
    NEW_ATTRIBUTES = building_id
    QUERY_EXPR:
      declare namespace gml="http://www.opengis.net/gml";
      declare namespace gen="http://www.opengis.net/citygml/generics/2.0";
      declare namespace bldg="http://www.opengis.net/citygml/building/2.0";

      fme:set-attribute('building_id', data(/Building/@gml_id))
    RESULT_ATTRIBUTE = _result
    RESULT_TYPE_NAME = Separated values
    SEPARATOR_VALUE = ,
    WRITE_XML_HEADER = No
    XML_ATTR = xml_fragment
    XML_REMOVE_SOURCE_ATTR = No
    XML_TYPE = Attribute specifying XML
    XQUERY_TYPE = XQuery expression
    QUERY_RESULTS -> AttributeManager
AttributeManager
    ATTR_TABLE:
      RENAME_SET_VALUE xml_fragment > xml_genericAttributeSet
      REMOVE xml_id
      REMOVE xml_matched_element
      REMOVE xml_parent_id
      REMOVE xml_parent_child_pos
      REMOVE _result
    -> FeatureJoiner_BuildingPart_2 [RIGHT]
    -> FeatureJoiner_Building_2 [RIGHT]
FeatureJoiner_BuildingPart_2
    ATTR_CONFLICT_RES = Prefer Left
    GEOMETRY_HANDLING = Prefer Left
    JOIN_KEYS = bldg_Building_gml_id building_id AUTO
    JOIN_MODE = Inner
    JOINED -> NullAttributeMapper_BuildingPart_2
NullAttributeMapper_BuildingPart_2
    ATTRCHOICE = Selected Attributes
    ATTRLIST = bldg_address bldg_Building_gml_id bldg_BuildingPart_gml_id bldg_class bldg_measuredHeight bldg_roofType bldg_storeyHeightsAboveGround bldg_storeysAboveGround bldg_storeysBelowGround bldg_usage1 bldg_usage2 bldg_usage3 bldg_usage4 bldg_usage5 bldg_usage6 bldg_usage7 bldg_usage8 bldg_usage9 bldg_usage10 bldg_yearOfConstruction bldg_yearOfDemolition core_creationDate core_terminationDate gml_description gml_name uro_BuildingDetailAttribute_areaClassificationType uro_BuildingDetailAttribute_basementFirstUsage uro_BuildingDetailAttribute_basementSecondUsage uro_BuildingDetailAttribute_basementUsage uro_BuildingDetailAttribute_buildingCoverageRate uro_BuildingDetailAttribute_buildingFootprintArea uro_BuildingDetailAttribute_buildingHeight uro_BuildingDetailAttribute_buildingRoofEdgeArea uro_BuildingDetailAttribute_buildingStructureOrgType uro_BuildingDetailAttribute_buildingStructureType uro_BuildingDetailAttribute_detailedUsage uro_BuildingDetailAttribute_detailedUsage2 uro_BuildingDetailAttribute_detailedUsage3 uro_BuildingDetailAttribute_developmentArea uro_BuildingDetailAttribute_districtsAndZonesType1 uro_BuildingDetailAttribute_districtsAndZonesType2 uro_BuildingDetailAttribute_districtsAndZonesType3 uro_BuildingDetailAttribute_districtsAndZonesType4 uro_BuildingDetailAttribute_districtsAndZonesType5 uro_BuildingDetailAttribute_districtsAndZonesType6 uro_BuildingDetailAttribute_districtsAndZonesType7 uro_BuildingDetailAttribute_districtsAndZonesType8 uro_BuildingDetailAttribute_districtsAndZonesType9 uro_BuildingDetailAttribute_districtsAndZonesType10 uro_BuildingDetailAttribute_eaveHeight uro_BuildingDetailAttribute_fireproofStructureType uro_BuildingDetailAttribute_floorAreaRate uro_BuildingDetailAttribute_groundFloorUsage uro_BuildingDetailAttribute_implementingBody uro_BuildingDetailAttribute_landUseType uro_BuildingDetailAttribute_majorUsage uro_BuildingDetailAttribute_majorUsage2 uro_BuildingDetailAttribute_note uro_BuildingDetailAttribute_orgUsage uro_BuildingDetailAttribute_orgUsage2 uro_BuildingDetailAttribute_reference uro_BuildingDetailAttribute_secondFloorUsage uro_BuildingDetailAttribute_serialNumberOfBuildingCertification uro_BuildingDetailAttribute_siteArea uro_BuildingDetailAttribute_specifiedBuildingCoverageRate uro_BuildingDetailAttribute_specifiedFloorAreaRate uro_BuildingDetailAttribute_standardFloorAreaRate uro_BuildingDetailAttribute_surveyYear uro_BuildingDetailAttribute_thirdFloorUsage uro_BuildingDetailAttribute_totalFloorArea uro_BuildingDetailAttribute_urbanPlanType uro_BuildingDetailAttribute_vacancy uro_buildingIDAttribute
    NULL_TREATMENT = Empty String
    SOURCE_ATTR_VAL = Null Empty "Missing (Selected Attributes Only)"
    -> Deaggregator_BuildingPart
Deaggregator_BuildingPart
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryPropertyExtractor_BuildingPart
GeometryPropertyExtractor_BuildingPart
    EXTRACTTYPE_PARAM = Geometry Name
    GEOM_NAME_FIELD = _geometry_name
    GQUERY:
      for $geom in //geometry
      where $geom/count(parent::geometry) = 0
      return number($geom/@fme_id)
    EXTRACTED -> AttributeEncoder_BuildingPart
AttributeEncoder_BuildingPart
    ATTRCHOICE = All Attributes
    DEST_ENCODING = utf-8
    TREAT_AS_BYTES = Honor Encoding
    -> TestFilter_BuildingPart
TestFilter_BuildingPart
    DEFAULT_VALUE = <UNFILTERED>
    PASSED_TEST_GROUP_OUTPUT = FIRST
    TEST_LIST:
      "BOOL_OP,OR,COMPOSITE_TEST,""""""1 OR 2"""""",TEST_CLAUSE,CASE_INSENSITIVE_TEST @Value(_geometry_name) BEGINS_WITH lod2
      CASE_INSENSITIVE_TEST @Value(_geometry_name) = surfaceMember",lod2_BuildingPart,"BOOL_OP,OR,COMPOSITE_TEST,""""""1"""""",TEST_CLAUSE,CASE_INSENSITIVE_TEST @Value(_geometry_name) BEGINS_WITH lod3",lod3_BuildingPart
    lod2_BuildingPart -> lod2_BuildingPart (writer GEODATABASE_FILE_1)
    lod3_BuildingPart -> lod3_BuildingPart (writer GEODATABASE_FILE_1)
FeatureJoiner_Building_2
    ATTR_CONFLICT_RES = Prefer Left
    GEOMETRY_HANDLING = Prefer Left
    JOIN_KEYS = bldg_Building_gml_id building_id AUTO
    JOIN_MODE = Inner
    JOINED -> NullAttributeMapper_Building
NullAttributeMapper_Building
    ATTRCHOICE = Selected Attributes
    ATTRLIST = bldg_Building_gml_id bldg_address bldg_class bldg_measuredHeight bldg_roofType bldg_storeyHeightsAboveGround bldg_storeyHeightsBelowGround bldg_storeysAboveGround bldg_storeysBelowGround bldg_usage1 bldg_usage10 bldg_usage2 bldg_usage3 bldg_usage4 bldg_usage5 bldg_usage6 bldg_usage7 bldg_usage8 bldg_usage9 bldg_yearOfConstruction bldg_yearOfDemolition building_id citygml_feature_role citygml_feature_role_attr_name citygml_feature_role_attr_val citygml_target_uri core_creationDate core_terminationDate gml_description gml_name gml_parent_id uro_BuildingDataQualityAttribute_appearanceSrcDesc1 uro_BuildingDataQualityAttribute_appearanceSrcDesc10 uro_BuildingDataQualityAttribute_appearanceSrcDesc2 uro_BuildingDataQualityAttribute_appearanceSrcDesc3 uro_BuildingDataQualityAttribute_appearanceSrcDesc4 uro_BuildingDataQualityAttribute_appearanceSrcDesc5 uro_BuildingDataQualityAttribute_appearanceSrcDesc6 uro_BuildingDataQualityAttribute_appearanceSrcDesc7 uro_BuildingDataQualityAttribute_appearanceSrcDesc8 uro_BuildingDataQualityAttribute_appearanceSrcDesc9 uro_BuildingDataQualityAttribute_geometrySrcDesc1 uro_BuildingDataQualityAttribute_geometrySrcDesc10 uro_BuildingDataQualityAttribute_geometrySrcDesc2 uro_BuildingDataQualityAttribute_geometrySrcDesc3 uro_BuildingDataQualityAttribute_geometrySrcDesc4 uro_BuildingDataQualityAttribute_geometrySrcDesc5 uro_BuildingDataQualityAttribute_geometrySrcDesc6 uro_BuildingDataQualityAttribute_geometrySrcDesc7 uro_BuildingDataQualityAttribute_geometrySrcDesc8 uro_BuildingDataQualityAttribute_geometrySrcDesc9 uro_BuildingDataQualityAttribute_lod1HeightType uro_BuildingDataQualityAttribute_lodType1 uro_BuildingDataQualityAttribute_lodType2 uro_BuildingDataQualityAttribute_lodType3 uro_BuildingDataQualityAttribute_srcScale1 uro_BuildingDataQualityAttribute_srcScale10 uro_BuildingDataQualityAttribute_srcScale2 uro_BuildingDataQualityAttribute_srcScale3 uro_BuildingDataQualityAttribute_srcScale4 uro_BuildingDataQualityAttribute_srcScale5 uro_BuildingDataQualityAttribute_srcScale6 uro_BuildingDataQualityAttribute_srcScale7 uro_BuildingDataQualityAttribute_srcScale8 uro_BuildingDataQualityAttribute_srcScale9 uro_BuildingDataQualityAttribute_thematicSrcDesc1 uro_BuildingDataQualityAttribute_thematicSrcDesc10 uro_BuildingDataQualityAttribute_thematicSrcDesc2 uro_BuildingDataQualityAttribute_thematicSrcDesc3 uro_BuildingDataQualityAttribute_thematicSrcDesc4 uro_BuildingDataQualityAttribute_thematicSrcDesc5 uro_BuildingDataQualityAttribute_thematicSrcDesc6 uro_BuildingDataQualityAttribute_thematicSrcDesc7 uro_BuildingDataQualityAttribute_thematicSrcDesc8 uro_BuildingDataQualityAttribute_thematicSrcDesc9 uro_BuildingDetailAttribute_areaClassificationType uro_BuildingDetailAttribute_basementFirstUsage uro_BuildingDetailAttribute_basementSecondUsage uro_BuildingDetailAttribute_basementUsage uro_BuildingDetailAttribute_buildingCoverageRate uro_BuildingDetailAttribute_buildingFootprintArea uro_BuildingDetailAttribute_buildingHeight uro_BuildingDetailAttribute_buildingRoofEdgeArea uro_BuildingDetailAttribute_buildingStructureOrgType uro_BuildingDetailAttribute_buildingStructureType uro_BuildingDetailAttribute_detailedUsage uro_BuildingDetailAttribute_detailedUsage2 uro_BuildingDetailAttribute_detailedUsage3 uro_BuildingDetailAttribute_developmentArea uro_BuildingDetailAttribute_districtsAndZonesType1 uro_BuildingDetailAttribute_districtsAndZonesType10 uro_BuildingDetailAttribute_districtsAndZonesType2 uro_BuildingDetailAttribute_districtsAndZonesType3 uro_BuildingDetailAttribute_districtsAndZonesType4 uro_BuildingDetailAttribute_districtsAndZonesType5 uro_BuildingDetailAttribute_districtsAndZonesType6 uro_BuildingDetailAttribute_districtsAndZonesType7 uro_BuildingDetailAttribute_districtsAndZonesType8 uro_BuildingDetailAttribute_districtsAndZonesType9 uro_BuildingDetailAttribute_eaveHeight uro_BuildingDetailAttribute_fireproofStructureType uro_BuildingDetailAttribute_floorAreaRate uro_BuildingDetailAttribute_groundFloorUsage uro_BuildingDetailAttribute_implementingBody uro_BuildingDetailAttribute_landUseType uro_BuildingDetailAttribute_majorUsage uro_BuildingDetailAttribute_majorUsage2 uro_BuildingDetailAttribute_note uro_BuildingDetailAttribute_orgUsage uro_BuildingDetailAttribute_orgUsage2 uro_BuildingDetailAttribute_reference uro_BuildingDetailAttribute_secondFloorUsage uro_BuildingDetailAttribute_serialNumberOfBuildingCertification uro_BuildingDetailAttribute_siteArea uro_BuildingDetailAttribute_specifiedBuildingCoverageRate uro_BuildingDetailAttribute_specifiedFloorAreaRate uro_BuildingDetailAttribute_standardFloorAreaRate uro_BuildingDetailAttribute_surveyYear uro_BuildingDetailAttribute_thirdFloorUsage uro_BuildingDetailAttribute_totalFloorArea uro_BuildingDetailAttribute_urbanPlanType uro_BuildingDetailAttribute_vacancy uro_KeyValuePairAttribute_codeValue1 uro_KeyValuePairAttribute_codeValue10 uro_KeyValuePairAttribute_codeValue2 uro_KeyValuePairAttribute_codeValue3 uro_KeyValuePairAttribute_codeValue4 uro_KeyValuePairAttribute_codeValue5 uro_KeyValuePairAttribute_codeValue6 uro_KeyValuePairAttribute_codeValue7 uro_KeyValuePairAttribute_codeValue8 uro_KeyValuePairAttribute_codeValue9 uro_KeyValuePairAttribute_key1 uro_KeyValuePairAttribute_key10 uro_KeyValuePairAttribute_key2 uro_KeyValuePairAttribute_key3 uro_KeyValuePairAttribute_key4 uro_KeyValuePairAttribute_key5 uro_KeyValuePairAttribute_key6 uro_KeyValuePairAttribute_key7 uro_KeyValuePairAttribute_key8 uro_KeyValuePairAttribute_key9 uro_LargeCustomerFacilityAttribute_areaClassificationType uro_LargeCustomerFacilityAttribute_availability uro_LargeCustomerFacilityAttribute_capacity uro_LargeCustomerFacilityAttribute_class uro_LargeCustomerFacilityAttribute_districtsAndZonesType1 uro_LargeCustomerFacilityAttribute_districtsAndZonesType10 uro_LargeCustomerFacilityAttribute_districtsAndZonesType2 uro_LargeCustomerFacilityAttribute_districtsAndZonesType3 uro_LargeCustomerFacilityAttribute_districtsAndZonesType4 uro_LargeCustomerFacilityAttribute_districtsAndZonesType5 uro_LargeCustomerFacilityAttribute_districtsAndZonesType6 uro_LargeCustomerFacilityAttribute_districtsAndZonesType7 uro_LargeCustomerFacilityAttribute_districtsAndZonesType8 uro_LargeCustomerFacilityAttribute_districtsAndZonesType9 uro_LargeCustomerFacilityAttribute_inauguralDate uro_LargeCustomerFacilityAttribute_keyTenants uro_LargeCustomerFacilityAttribute_landUseType uro_LargeCustomerFacilityAttribute_name uro_LargeCustomerFacilityAttribute_note uro_LargeCustomerFacilityAttribute_owner uro_LargeCustomerFacilityAttribute_reference uro_LargeCustomerFacilityAttribute_surveyYear uro_LargeCustomerFacilityAttribute_totalFloorArea uro_LargeCustomerFacilityAttribute_totalStoreFloorArea uro_LargeCustomerFacilityAttribute_urbanPlanType uro_buildingIDAttribute xml_genericAttributeSet uro_buildingIDAttribute_branchID uro_buildingIDAttribute_buildingID uro_buildingIDAttribute_city uro_buildingIDAttribute_partID uro_buildingIDAttribute_prefecture uro_BuildingHighTideRiskAttribute_depth uro_BuildingHighTideRiskAttribute_description uro_BuildingHighTideRiskAttribute_rank uro_BuildingHighTideRiskAttribute_rankOrg uro_BuildingInlandFloodingRiskAttribute_depth uro_BuildingInlandFloodingRiskAttribute_description uro_BuildingInlandFloodingRiskAttribute_rank uro_BuildingInlandFloodingRiskAttribute_rankOrg uro_BuildingLandSlideRiskAttribute_areaType1 uro_BuildingLandSlideRiskAttribute_areaType2 uro_BuildingLandSlideRiskAttribute_areaType3 uro_BuildingLandSlideRiskAttribute_description1 uro_BuildingLandSlideRiskAttribute_description2 uro_BuildingLandSlideRiskAttribute_description3 uro_BuildingRiverFloodingRiskAttribute_adminType uro_BuildingRiverFloodingRiskAttribute_depth uro_BuildingRiverFloodingRiskAttribute_description uro_BuildingRiverFloodingRiskAttribute_duration uro_BuildingRiverFloodingRiskAttribute_rank uro_BuildingRiverFloodingRiskAttribute_rankOrg uro_BuildingRiverFloodingRiskAttribute_scale uro_BuildingTsunamiRiskAttribute_depth uro_BuildingTsunamiRiskAttribute_description uro_BuildingTsunamiRiskAttribute_rank uro_BuildingTsunamiRiskAttribute_rankOrg
    NULL_TREATMENT = Empty String
    SOURCE_ATTR_VAL = Null Empty "Missing (Selected Attributes Only)"
    -> Deaggregator_Building
Deaggregator_Building
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryPropertyExtractor_Building
GeometryPropertyExtractor_Building
    EXTRACTTYPE_PARAM = Geometry Name
    GEOM_NAME_FIELD = _geometry_name
    GQUERY:
      for $geom in //geometry
      where $geom/count(parent::geometry) = 0
      return number($geom/@fme_id)
    EXTRACTED -> AttributeEncoder
AttributeEncoder
    ATTRCHOICE = Selected Attributes
    ATTRLIST = _geometry_name _part_number bldg_address bldg_Building_gml_id bldg_class bldg_measuredHeight bldg_roofType bldg_storeyHeightsAboveGround bldg_storeyHeightsBelowGround bldg_storeysAboveGround bldg_storeysBelowGround bldg_usage1 bldg_usage2 bldg_usage3 bldg_usage4 bldg_usage5 bldg_usage6 bldg_usage7 bldg_usage8 bldg_usage9 bldg_usage10 bldg_yearOfConstruction bldg_yearOfDemolition building_id citygml_feature_role citygml_feature_role_attr_name citygml_feature_role_attr_val citygml_target_uri core_creationDate core_terminationDate gml_description gml_name gml_parent_id uro_BuildingDataQualityAttribute_appearanceSrcDesc1 uro_BuildingDataQualityAttribute_appearanceSrcDesc2 uro_BuildingDataQualityAttribute_appearanceSrcDesc3 uro_BuildingDataQualityAttribute_appearanceSrcDesc4 uro_BuildingDataQualityAttribute_appearanceSrcDesc5 uro_BuildingDataQualityAttribute_appearanceSrcDesc6 uro_BuildingDataQualityAttribute_appearanceSrcDesc7 uro_BuildingDataQualityAttribute_appearanceSrcDesc8 uro_BuildingDataQualityAttribute_appearanceSrcDesc9 uro_BuildingDataQualityAttribute_appearanceSrcDesc10 uro_BuildingDataQualityAttribute_geometrySrcDesc1 uro_BuildingDataQualityAttribute_geometrySrcDesc2 uro_BuildingDataQualityAttribute_geometrySrcDesc3 uro_BuildingDataQualityAttribute_geometrySrcDesc4 uro_BuildingDataQualityAttribute_geometrySrcDesc5 uro_BuildingDataQualityAttribute_geometrySrcDesc6 uro_BuildingDataQualityAttribute_geometrySrcDesc7 uro_BuildingDataQualityAttribute_geometrySrcDesc8 uro_BuildingDataQualityAttribute_geometrySrcDesc9 uro_BuildingDataQualityAttribute_geometrySrcDesc10 uro_BuildingDataQualityAttribute_lod1HeightType uro_BuildingDataQualityAttribute_lodType1 uro_BuildingDataQualityAttribute_lodType2 uro_BuildingDataQualityAttribute_lodType3 uro_BuildingDataQualityAttribute_srcScale1 uro_BuildingDataQualityAttribute_srcScale2 uro_BuildingDataQualityAttribute_srcScale3 uro_BuildingDataQualityAttribute_srcScale4 uro_BuildingDataQualityAttribute_srcScale5 uro_BuildingDataQualityAttribute_srcScale6 uro_BuildingDataQualityAttribute_srcScale7 uro_BuildingDataQualityAttribute_srcScale8 uro_BuildingDataQualityAttribute_srcScale9 uro_BuildingDataQualityAttribute_srcScale10 uro_BuildingDataQualityAttribute_thematicSrcDesc1 uro_BuildingDataQualityAttribute_thematicSrcDesc2 uro_BuildingDataQualityAttribute_thematicSrcDesc3 uro_BuildingDataQualityAttribute_thematicSrcDesc4 uro_BuildingDataQualityAttribute_thematicSrcDesc5 uro_BuildingDataQualityAttribute_thematicSrcDesc6 uro_BuildingDataQualityAttribute_thematicSrcDesc7 uro_BuildingDataQualityAttribute_thematicSrcDesc8 uro_BuildingDataQualityAttribute_thematicSrcDesc9 uro_BuildingDataQualityAttribute_thematicSrcDesc10 uro_BuildingDetailAttribute_areaClassificationType uro_BuildingDetailAttribute_basementFirstUsage uro_BuildingDetailAttribute_basementSecondUsage uro_BuildingDetailAttribute_basementUsage uro_BuildingDetailAttribute_buildingCoverageRate uro_BuildingDetailAttribute_buildingFootprintArea uro_BuildingDetailAttribute_buildingHeight uro_BuildingDetailAttribute_buildingRoofEdgeArea uro_BuildingDetailAttribute_buildingStructureOrgType uro_BuildingDetailAttribute_buildingStructureType uro_BuildingDetailAttribute_detailedUsage uro_BuildingDetailAttribute_detailedUsage2 uro_BuildingDetailAttribute_detailedUsage3 uro_BuildingDetailAttribute_developmentArea uro_BuildingDetailAttribute_districtsAndZonesType1 uro_BuildingDetailAttribute_districtsAndZonesType2 uro_BuildingDetailAttribute_districtsAndZonesType3 uro_BuildingDetailAttribute_districtsAndZonesType4 uro_BuildingDetailAttribute_districtsAndZonesType5 uro_BuildingDetailAttribute_districtsAndZonesType6 uro_BuildingDetailAttribute_districtsAndZonesType7 uro_BuildingDetailAttribute_districtsAndZonesType8 uro_BuildingDetailAttribute_districtsAndZonesType9 uro_BuildingDetailAttribute_districtsAndZonesType10 uro_BuildingDetailAttribute_eaveHeight uro_BuildingDetailAttribute_fireproofStructureType uro_BuildingDetailAttribute_floorAreaRate uro_BuildingDetailAttribute_groundFloorUsage uro_BuildingDetailAttribute_implementingBody uro_BuildingDetailAttribute_landUseType uro_BuildingDetailAttribute_majorUsage uro_BuildingDetailAttribute_majorUsage2 uro_BuildingDetailAttribute_note uro_BuildingDetailAttribute_orgUsage uro_BuildingDetailAttribute_orgUsage2 uro_BuildingDetailAttribute_reference uro_BuildingDetailAttribute_secondFloorUsage uro_BuildingDetailAttribute_serialNumberOfBuildingCertification uro_BuildingDetailAttribute_siteArea uro_BuildingDetailAttribute_specifiedBuildingCoverageRate uro_BuildingDetailAttribute_specifiedFloorAreaRate uro_BuildingDetailAttribute_standardFloorAreaRate uro_BuildingDetailAttribute_surveyYear uro_BuildingDetailAttribute_thirdFloorUsage uro_BuildingDetailAttribute_totalFloorArea uro_BuildingDetailAttribute_urbanPlanType uro_BuildingDetailAttribute_vacancy uro_BuildingHighTideRiskAttribute_depth uro_BuildingHighTideRiskAttribute_description uro_BuildingHighTideRiskAttribute_rank uro_BuildingHighTideRiskAttribute_rankOrg uro_buildingIDAttribute uro_buildingIDAttribute_branchID uro_buildingIDAttribute_buildingID uro_buildingIDAttribute_city uro_buildingIDAttribute_partID uro_buildingIDAttribute_prefecture uro_BuildingInlandFloodingRiskAttribute_depth uro_BuildingInlandFloodingRiskAttribute_description uro_BuildingInlandFloodingRiskAttribute_rank uro_BuildingInlandFloodingRiskAttribute_rankOrg uro_BuildingLandSlideRiskAttribute_areaType1 uro_BuildingLandSlideRiskAttribute_areaType2 uro_BuildingLandSlideRiskAttribute_areaType3 uro_BuildingLandSlideRiskAttribute_description1 uro_BuildingLandSlideRiskAttribute_description2 uro_BuildingLandSlideRiskAttribute_description3 uro_BuildingRiverFloodingRiskAttribute_adminType uro_BuildingRiverFloodingRiskAttribute_depth uro_BuildingRiverFloodingRiskAttribute_description uro_BuildingRiverFloodingRiskAttribute_duration uro_BuildingRiverFloodingRiskAttribute_rank uro_BuildingRiverFloodingRiskAttribute_rankOrg uro_BuildingRiverFloodingRiskAttribute_scale uro_BuildingTsunamiRiskAttribute_depth uro_BuildingTsunamiRiskAttribute_description uro_BuildingTsunamiRiskAttribute_rank uro_BuildingTsunamiRiskAttribute_rankOrg uro_KeyValuePairAttribute_codeValue1 uro_KeyValuePairAttribute_codeValue2 uro_KeyValuePairAttribute_codeValue3 uro_KeyValuePairAttribute_codeValue4 uro_KeyValuePairAttribute_codeValue5 uro_KeyValuePairAttribute_codeValue6 uro_KeyValuePairAttribute_codeValue7 uro_KeyValuePairAttribute_codeValue8 uro_KeyValuePairAttribute_codeValue9 uro_KeyValuePairAttribute_codeValue10 uro_KeyValuePairAttribute_key1 uro_KeyValuePairAttribute_key2 uro_KeyValuePairAttribute_key3 uro_KeyValuePairAttribute_key4 uro_KeyValuePairAttribute_key5 uro_KeyValuePairAttribute_key6 uro_KeyValuePairAttribute_key7 uro_KeyValuePairAttribute_key8 uro_KeyValuePairAttribute_key9 uro_KeyValuePairAttribute_key10 uro_LargeCustomerFacilityAttribute_areaClassificationType uro_LargeCustomerFacilityAttribute_availability uro_LargeCustomerFacilityAttribute_capacity uro_LargeCustomerFacilityAttribute_class uro_LargeCustomerFacilityAttribute_districtsAndZonesType1 uro_LargeCustomerFacilityAttribute_districtsAndZonesType2 uro_LargeCustomerFacilityAttribute_districtsAndZonesType3 uro_LargeCustomerFacilityAttribute_districtsAndZonesType4 uro_LargeCustomerFacilityAttribute_districtsAndZonesType5 uro_LargeCustomerFacilityAttribute_districtsAndZonesType6 uro_LargeCustomerFacilityAttribute_districtsAndZonesType7 uro_LargeCustomerFacilityAttribute_districtsAndZonesType8 uro_LargeCustomerFacilityAttribute_districtsAndZonesType9 uro_LargeCustomerFacilityAttribute_districtsAndZonesType10 uro_LargeCustomerFacilityAttribute_inauguralDate uro_LargeCustomerFacilityAttribute_keyTenants uro_LargeCustomerFacilityAttribute_landUseType uro_LargeCustomerFacilityAttribute_name uro_LargeCustomerFacilityAttribute_note uro_LargeCustomerFacilityAttribute_owner uro_LargeCustomerFacilityAttribute_reference uro_LargeCustomerFacilityAttribute_surveyYear uro_LargeCustomerFacilityAttribute_totalFloorArea uro_LargeCustomerFacilityAttribute_totalStoreFloorArea uro_LargeCustomerFacilityAttribute_urbanPlanType xml_genericAttributeSet
    DEST_ENCODING = utf-8
    TREAT_AS_BYTES = Honor Encoding
    -> TestFilter_Building
TestFilter_Building
    DEFAULT_VALUE = <UNFILTERED>
    PASSED_TEST_GROUP_OUTPUT = FIRST
    TEST_LIST = "BOOL_OP,OR,COMPOSITE_TEST,""""""1"""""",TEST_CLAUSE,CASE_INSENSITIVE_TEST @Value(_geometry_name) BEGINS_WITH lod0",lod0_Building,"BOOL_OP,OR,COMPOSITE_TEST,""""""1"""""",TEST_CLAUSE,CASE_INSENSITIVE_TEST @Value(_geometry_name) BEGINS_WITH lod1",lod1_Building,"BOOL_OP,OR,COMPOSITE_TEST,""""""1"""""",TEST_CLAUSE,CASE_INSENSITIVE_TEST @Value(_geometry_name) BEGINS_WITH lod2",lod2_Building,"BOOL_OP,OR,COMPOSITE_TEST,""""""1"""""",TEST_CLAUSE,CASE_INSENSITIVE_TEST @Value(_geometry_name) BEGINS_WITH lod3",lod3_Building
    lod0_Building -> GeometryPartExtractor
    lod1_Building -> lod1_Building (writer GEODATABASE_FILE_1)
    lod2_Building -> lod2_Building (writer GEODATABASE_FILE_1)
    lod3_Building -> lod3_Building (writer GEODATABASE_FILE_1)
GeometryPartExtractor
    GQUERY:
      for $geom in //geometry
      where $geom/parent::geometry/@fme_geometry_type = 'IFMEFace'
      return number($geom/@fme_id)
    EXTRACTED -> lod0_Building (writer GEODATABASE_FILE_1)

Bookmark: CityGML 建物データ
ClosureSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer
    -> Deaggregator_CloserSurface
BuildingInstallation (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer
    -> Deaggregator_BuildingInstallation
Window (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer
    -> AttributeManager_Window
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer
    -> Deaggregator_WallSurface
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer
    -> Deaggregator_RoofSurface
OuterFloorSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer
    -> Deaggregator_OuterFloorSurface
OuterCeilingSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer
    -> AttributeManager_OuterCeilingSurface
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer
    -> Deaggregator_GroundSurface
CityModel (reader CITYGML_1)
    attributes: citygml_target_uri xml_buffer, gml_description xml_buffer, gml_name xml_buffer, citygml_city_object_member{}.xlink_href xml_buffer, gml_feature_member{}.xlink_href xml_buffer
Door (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_address{}.xlink_href xml_buffer
    -> AttributeManager_Door
BuildingPart (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer,
      citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, uro_building_data_quality_attribute{}.uro_building_data_quality_attribute_uro_src_scale{} xml_buffer, uro_building_data_quality_attribute{}.uro_building_data_quality_attribute_uro_src_scale{}.codeSpace xml_buffer, uro_building_data_quality_attribute{}.uro_building_data_quality_attribute_uro_geometry_src_desc{} xml_buffer, uro_building_data_quality_attribute{}.uro_building_data_quality_attribute_uro_geometry_src_desc{}.codeSpace xml_buffer, uro_building_data_quality_attribute{}.uro_building_data_quality_attribute_uro_thematic_src_desc{} xml_buffer, uro_building_data_quality_attribute{}.uro_building_data_quality_attribute_uro_thematic_src_desc{}.codeSpace xml_buffer, uro_building_data_quality_attribute{}.uro_building_data_quality_attribute_uro_appearance_src_desc{} xml_buffer, uro_building_data_quality_attribute{}.uro_building_data_quality_attribute_uro_appearance_src_desc{}.codeSpace xml_buffer, uro_building_data_quality_attribute{}.uro_building_data_quality_attribute_uro_lod1_height_type xml_buffer, uro_building_data_quality_attribute{}.uro_building_data_quality_attribute_uro_lod1_height_type_codeSpace xml_buffer, uro_building_data_quality_attribute{}.uro_building_data_quality_attribute_uro_lod_type{} xml_char(3), uro_building_detail_attribute{}.uro_building_detail_attribute_uro_serial_number_of_building_certification xml_buffer, uro_building_detail_attribute{}.uro_building_detail_attribute_uro_site_area xml_real64, uro_building_detail_attribute{}.uro_building_detail_attribute_uro_site_area_units xml_buffer, uro_building_detail_attribute{}.uro_building_detail_attribute_uro_total_floor_area xml_real64, uro_building_detail_attribute{}.uro_building_detail_attribute_uro_total_floor_area_units xml_buffer, uro_building_detail_attribute{}.uro_building_detail_attribute_uro_building_footprint_area xml_real64, uro_building_detail_attribute{}.uro_building_detail_attribute_uro_building_footprint_area_units xml_buffer, uro_building_detail_attribute{}.uro_building_detail_attribute_uro_building_roof_edge_area xml_real64, uro_building_detail_attribute{}.uro_building_detail_attribute_uro_building_roof_edge_area_units xml_buffer, uro_building_detail_attribute{}.uro_building_detail_attribute_uro_development_area xml_real64,
      uro_building_detail_attribute{}.uro_building_detail_attribute_uro_development_area_units xml_buffer, uro_building_detail_attribute{}.uro_building_detail_attribute_uro_building_structure_type xml_buffer, uro_building_detail_attribute{}.uro_building_detail_attribute_uro_building_structure_type_codeSpace xml_buffer, uro_building_detail_attribute{}.uro_building_detail_attribute_uro_building_structure_org_type xml_buffer, uro_building_detail_attribute{}.uro_building_detail_attribute_uro_building_structure_org_type_codeSpace xml_buffer, uro_building_detail_attribute{}.uro_building_detail_attribute_uro_fireproof_structure_type xml_buffer, uro_building_detail_attribute{}.uro_building_detail_attribute_uro_fireproof_structure_type_codeSpace xml_buffer, uro_building_detail_attribute{}.uro_building_detail_attribute_uro_implementing_body xml_buffer, uro_building_detail_attribute{}.uro_building_detail_attribute_uro_urban_plan_type xml_buffer, uro_building_detail_attribute{}.uro_building_detail_attribute_uro_urban_plan_type_codeSpace xml_buffer, uro_building_detail_attribute{}.uro_building_detail_attribute_uro_area_classification_type xml_buffer, uro_building_detail_attribute{}.uro_building_detail_attribute_uro_area_classification_type_codeSpace xml_buffer, uro_building_detail_attribute{}.uro_building_detail_attribute_uro_districts_and_zones_type{} xml_buffer, uro_building_detail_attribute{}.uro_building_detail_attribute_uro_districts_and_zones_type{}.codeSpace xml_buffer, uro_building_detail_attribute{}.uro_building_detail_attribute_uro_land_use_type xml_buffer, uro_building_detail_attribute{}.uro_building_detail_attribute_uro_land_use_type_codeSpace xml_buffer, uro_building_detail_attribute{}.uro_building_detail_attribute_uro_reference xml_buffer, uro_building_detail_attribute{}.uro_building_detail_attribute_uro_major_usage xml_buffer, uro_building_detail_attribute{}.uro_building_detail_attribute_uro_major_usage_codeSpace xml_buffer, uro_building_detail_attribute{}.uro_building_detail_attribute_uro_major_usage2 xml_buffer, uro_building_detail_attribute{}.uro_building_detail_attribute_uro_major_usage2_codeSpace xml_buffer, uro_building_detail_attribute{}.uro_building_detail_attribute_uro_org_usage xml_buffer, uro_building_detail_attribute{}.uro_building_detail_attribute_uro_org_usage_codeSpace xml_buffer, uro_building_detail_attribute{}.uro_building_detail_attribute_uro_org_usage2 xml_buffer, uro_building_detail_attribute{}.uro_building_detail_attribute_uro_org_usage2_codeSpace xml_buffer, uro_building_detail_attribute{}.uro_building_detail_attribute_uro_detailed_usage xml_buffer, uro_building_detail_attribute{}.uro_building_detail_attribute_uro_detailed_usage_codeSpace xml_buffer, uro_building_detail_attribute{}.uro_building_detail_attribute_uro_detailed_usage2 xml_buffer, uro_building_detail_attribute{}.uro_building_detail_attribute_uro_detailed_usage2_codeSpace xml_buffer, uro_building_detail_attribute{}.uro_building_detail_attribute_uro_detailed_usage3 xml_buffer,
      uro_building_detail_attribute{}.uro_building_detail_attribute_uro_detailed_usage3_codeSpace xml_buffer, uro_building_detail_attribute{}.uro_building_detail_attribute_uro_ground_floor_usage xml_buffer, uro_building_detail_attribute{}.uro_building_detail_attribute_uro_ground_floor_usage_codeSpace xml_buffer, uro_building_detail_attribute{}.uro_building_detail_attribute_uro_second_floor_usage xml_buffer, uro_building_detail_attribute{}.uro_building_detail_attribute_uro_second_floor_usage_codeSpace xml_buffer, uro_building_detail_attribute{}.uro_building_detail_attribute_uro_third_floor_usage xml_buffer, uro_building_detail_attribute{}.uro_building_detail_attribute_uro_third_floor_usage_codeSpace xml_buffer, uro_building_detail_attribute{}.uro_building_detail_attribute_uro_basement_usage xml_buffer, uro_building_detail_attribute{}.uro_building_detail_attribute_uro_basement_usage_codeSpace xml_buffer, uro_building_detail_attribute{}.uro_building_detail_attribute_uro_basement_first_usage xml_buffer, uro_building_detail_attribute{}.uro_building_detail_attribute_uro_basement_first_usage_codeSpace xml_buffer, uro_building_detail_attribute{}.uro_building_detail_attribute_uro_basement_second_usage xml_buffer, uro_building_detail_attribute{}.uro_building_detail_attribute_uro_basement_second_usage_codeSpace xml_buffer, uro_building_detail_attribute{}.uro_building_detail_attribute_uro_vacancy xml_buffer, uro_building_detail_attribute{}.uro_building_detail_attribute_uro_vacancy_codeSpace xml_buffer, uro_building_detail_attribute{}.uro_building_detail_attribute_uro_building_coverage_rate xml_real64, uro_building_detail_attribute{}.uro_building_detail_attribute_uro_floor_area_rate xml_real64, uro_building_detail_attribute{}.uro_building_detail_attribute_uro_specified_building_coverage_rate xml_real64, uro_building_detail_attribute{}.uro_building_detail_attribute_uro_specified_floor_area_rate xml_real64, uro_building_detail_attribute{}.uro_building_detail_attribute_uro_standard_floor_area_rate xml_real64, uro_building_detail_attribute{}.uro_building_detail_attribute_uro_building_height xml_real64, uro_building_detail_attribute{}.uro_building_detail_attribute_uro_building_height_units xml_buffer, uro_building_detail_attribute{}.uro_building_detail_attribute_uro_eave_height xml_real64, uro_building_detail_attribute{}.uro_building_detail_attribute_uro_eave_height_units xml_buffer, uro_building_detail_attribute{}.uro_building_detail_attribute_uro_note xml_buffer, uro_building_detail_attribute{}.uro_building_detail_attribute_uro_survey_year xml_buffer, uro_building_disaster_risk_attribute{}.uro_building_high_tide_risk_attribute_uro_description xml_buffer, uro_building_disaster_risk_attribute{}.uro_building_high_tide_risk_attribute_uro_description_codeSpace xml_buffer, uro_building_disaster_risk_attribute{}.uro_building_high_tide_risk_attribute_uro_rank xml_buffer, uro_building_disaster_risk_attribute{}.uro_building_high_tide_risk_attribute_uro_rank_codeSpace xml_buffer,
      uro_building_disaster_risk_attribute{}.uro_building_high_tide_risk_attribute_uro_rank_org xml_buffer, uro_building_disaster_risk_attribute{}.uro_building_high_tide_risk_attribute_uro_rank_org_codeSpace xml_buffer, uro_building_disaster_risk_attribute{}.uro_building_high_tide_risk_attribute_uro_depth xml_real64, uro_building_disaster_risk_attribute{}.uro_building_high_tide_risk_attribute_uro_depth_units xml_buffer, uro_building_disaster_risk_attribute{}.uro_building_inland_flooding_risk_attribute_uro_description xml_buffer, uro_building_disaster_risk_attribute{}.uro_building_inland_flooding_risk_attribute_uro_description_codeSpace xml_buffer, uro_building_disaster_risk_attribute{}.uro_building_inland_flooding_risk_attribute_uro_rank xml_buffer, uro_building_disaster_risk_attribute{}.uro_building_inland_flooding_risk_attribute_uro_rank_codeSpace xml_buffer, uro_building_disaster_risk_attribute{}.uro_building_inland_flooding_risk_attribute_uro_rank_org xml_buffer, uro_building_disaster_risk_attribute{}.uro_building_inland_flooding_risk_attribute_uro_rank_org_codeSpace xml_buffer, uro_building_disaster_risk_attribute{}.uro_building_inland_flooding_risk_attribute_uro_depth xml_real64, uro_building_disaster_risk_attribute{}.uro_building_inland_flooding_risk_attribute_uro_depth_units xml_buffer, uro_building_disaster_risk_attribute{}.uro_building_land_slide_risk_attribute_uro_description xml_buffer, uro_building_disaster_risk_attribute{}.uro_building_land_slide_risk_attribute_uro_description_codeSpace xml_buffer, uro_building_disaster_risk_attribute{}.uro_building_land_slide_risk_attribute_uro_area_type xml_buffer, uro_building_disaster_risk_attribute{}.uro_building_land_slide_risk_attribute_uro_area_type_codeSpace xml_buffer, uro_building_disaster_risk_attribute{}.uro_building_river_flooding_risk_attribute_uro_description xml_buffer, uro_building_disaster_risk_attribute{}.uro_building_river_flooding_risk_attribute_uro_description_codeSpace xml_buffer, uro_building_disaster_risk_attribute{}.uro_building_river_flooding_risk_attribute_uro_rank xml_buffer, uro_building_disaster_risk_attribute{}.uro_building_river_flooding_risk_attribute_uro_rank_codeSpace xml_buffer, uro_building_disaster_risk_attribute{}.uro_building_river_flooding_risk_attribute_uro_rank_org xml_buffer, uro_building_disaster_risk_attribute{}.uro_building_river_flooding_risk_attribute_uro_rank_org_codeSpace xml_buffer, uro_building_disaster_risk_attribute{}.uro_building_river_flooding_risk_attribute_uro_depth xml_real64, uro_building_disaster_risk_attribute{}.uro_building_river_flooding_risk_attribute_uro_depth_units xml_buffer, uro_building_disaster_risk_attribute{}.uro_building_river_flooding_risk_attribute_uro_admin_type xml_buffer, uro_building_disaster_risk_attribute{}.uro_building_river_flooding_risk_attribute_uro_admin_type_codeSpace xml_buffer, uro_building_disaster_risk_attribute{}.uro_building_river_flooding_risk_attribute_uro_scale xml_buffer, uro_building_disaster_risk_attribute{}.uro_building_river_flooding_risk_attribute_uro_scale_codeSpace xml_buffer, uro_building_disaster_risk_attribute{}.uro_building_river_flooding_risk_attribute_uro_duration xml_real64, uro_building_disaster_risk_attribute{}.uro_building_river_flooding_risk_attribute_uro_duration_units xml_buffer,
      uro_building_disaster_risk_attribute{}.uro_building_tsunami_risk_attribute_uro_description xml_buffer, uro_building_disaster_risk_attribute{}.uro_building_tsunami_risk_attribute_uro_description_codeSpace xml_buffer, uro_building_disaster_risk_attribute{}.uro_building_tsunami_risk_attribute_uro_rank xml_buffer, uro_building_disaster_risk_attribute{}.uro_building_tsunami_risk_attribute_uro_rank_codeSpace xml_buffer, uro_building_disaster_risk_attribute{}.uro_building_tsunami_risk_attribute_uro_rank_org xml_buffer, uro_building_disaster_risk_attribute{}.uro_building_tsunami_risk_attribute_uro_rank_org_codeSpace xml_buffer, uro_building_disaster_risk_attribute{}.uro_building_tsunami_risk_attribute_uro_depth xml_real64, uro_building_disaster_risk_attribute{}.uro_building_tsunami_risk_attribute_uro_depth_units xml_buffer, uro_building_idattribute{}.uro_building_idattribute_uro_building_id xml_buffer, uro_building_idattribute{}.uro_building_idattribute_uro_branch_id xml_int64, uro_building_idattribute{}.uro_building_idattribute_uro_part_id xml_int64, uro_building_idattribute{}.uro_building_idattribute_uro_prefecture xml_buffer, uro_building_idattribute{}.uro_building_idattribute_uro_prefecture_codeSpace xml_buffer, uro_building_idattribute{}.uro_building_idattribute_uro_city xml_buffer, uro_building_idattribute{}.uro_building_idattribute_uro_city_codeSpace xml_buffer, uro_key_value_pair_attribute{}.uro_key_value_pair_attribute_uro_key xml_buffer, uro_key_value_pair_attribute{}.uro_key_value_pair_attribute_uro_key_codeSpace xml_buffer, uro_key_value_pair_attribute{}.uro_key_value_pair_attribute_uro_code_value xml_buffer, uro_key_value_pair_attribute{}.uro_key_value_pair_attribute_uro_code_value_codeSpace xml_buffer, uro_key_value_pair_attribute{}.uro_key_value_pair_attribute_uro_string_value xml_buffer, uro_key_value_pair_attribute{}.uro_key_value_pair_attribute_uro_int_value xml_int64, uro_key_value_pair_attribute{}.uro_key_value_pair_attribute_uro_double_value xml_real64, uro_key_value_pair_attribute{}.uro_key_value_pair_attribute_uro_measured_value xml_real64, uro_key_value_pair_attribute{}.uro_key_value_pair_attribute_uro_measured_value_units xml_buffer, uro_key_value_pair_attribute{}.uro_key_value_pair_attribute_uro_date_value xml_date, uro_key_value_pair_attribute{}.uro_key_value_pair_attribute_uro_uri_value xml_buffer, uro_large_customer_facility_attribute{}.uro_large_customer_facility_attribute_uro_class xml_buffer, uro_large_customer_facility_attribute{}.uro_large_customer_facility_attribute_uro_class_codeSpace xml_buffer, uro_large_customer_facility_attribute{}.uro_large_customer_facility_attribute_uro_name xml_buffer, uro_large_customer_facility_attribute{}.uro_large_customer_facility_attribute_uro_capacity xml_int64,
      uro_large_customer_facility_attribute{}.uro_large_customer_facility_attribute_uro_owner xml_buffer, uro_large_customer_facility_attribute{}.uro_large_customer_facility_attribute_uro_total_floor_area xml_real64, uro_large_customer_facility_attribute{}.uro_large_customer_facility_attribute_uro_total_floor_area_units xml_buffer, uro_large_customer_facility_attribute{}.uro_large_customer_facility_attribute_uro_total_store_floor_area xml_real64, uro_large_customer_facility_attribute{}.uro_large_customer_facility_attribute_uro_total_store_floor_area_units xml_buffer, uro_large_customer_facility_attribute{}.uro_large_customer_facility_attribute_uro_inaugural_date xml_date, uro_large_customer_facility_attribute{}.uro_large_customer_facility_attribute_uro_key_tenants xml_buffer, uro_large_customer_facility_attribute{}.uro_large_customer_facility_attribute_uro_availability xml_boolean, uro_large_customer_facility_attribute{}.uro_large_customer_facility_attribute_uro_urban_plan_type xml_buffer, uro_large_customer_facility_attribute{}.uro_large_customer_facility_attribute_uro_urban_plan_type_codeSpace xml_buffer, uro_large_customer_facility_attribute{}.uro_large_customer_facility_attribute_uro_area_classification_type xml_buffer, uro_large_customer_facility_attribute{}.uro_large_customer_facility_attribute_uro_area_classification_type_codeSpace xml_buffer, uro_large_customer_facility_attribute{}.uro_large_customer_facility_attribute_uro_districts_and_zones_type{} xml_buffer, uro_large_customer_facility_attribute{}.uro_large_customer_facility_attribute_uro_districts_and_zones_type{}.codeSpace xml_buffer, uro_large_customer_facility_attribute{}.uro_large_customer_facility_attribute_uro_land_use_type xml_buffer, uro_large_customer_facility_attribute{}.uro_large_customer_facility_attribute_uro_land_use_type_codeSpace xml_buffer, uro_large_customer_facility_attribute{}.uro_large_customer_facility_attribute_uro_reference xml_buffer, uro_large_customer_facility_attribute{}.uro_large_customer_facility_attribute_uro_note xml_buffer, uro_large_customer_facility_attribute{}.uro_large_customer_facility_attribute_uro_survey_year xml_buffer
    -> FeatureJoiner_BuildingPart [LEFT]
BuildingFurniture (reader CITYGML_1)
    attributes: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
Address (reader CITYGML_1)
    attributes: citygml_target_uri xml_buffer, citygml_feature_role xml_buffer, citygml_feature_role_attr_name xml_buffer, citygml_feature_role_attr_val xml_buffer, gml_description xml_buffer, gml_name xml_buffer, citygml_address xml_xml
    -> XMLFlattener
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer,
      citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, uro_building_data_quality_attribute{}.uro_building_data_quality_attribute_uro_src_scale{} xml_buffer, uro_building_data_quality_attribute{}.uro_building_data_quality_attribute_uro_src_scale{}.codeSpace xml_buffer, uro_building_data_quality_attribute{}.uro_building_data_quality_attribute_uro_geometry_src_desc{} xml_buffer, uro_building_data_quality_attribute{}.uro_building_data_quality_attribute_uro_geometry_src_desc{}.codeSpace xml_buffer, uro_building_data_quality_attribute{}.uro_building_data_quality_attribute_uro_thematic_src_desc{} xml_buffer, uro_building_data_quality_attribute{}.uro_building_data_quality_attribute_uro_thematic_src_desc{}.codeSpace xml_buffer, uro_building_data_quality_attribute{}.uro_building_data_quality_attribute_uro_appearance_src_desc{} xml_buffer, uro_building_data_quality_attribute{}.uro_building_data_quality_attribute_uro_appearance_src_desc{}.codeSpace xml_buffer, uro_building_data_quality_attribute{}.uro_building_data_quality_attribute_uro_lod1_height_type xml_buffer, uro_building_data_quality_attribute{}.uro_building_data_quality_attribute_uro_lod1_height_type_codeSpace xml_buffer, uro_building_data_quality_attribute{}.uro_building_data_quality_attribute_uro_lod_type{} xml_char(3), uro_building_detail_attribute{}.uro_building_detail_attribute_uro_serial_number_of_building_certification xml_buffer, uro_building_detail_attribute{}.uro_building_detail_attribute_uro_site_area xml_real64, uro_building_detail_attribute{}.uro_building_detail_attribute_uro_site_area_units xml_buffer, uro_building_detail_attribute{}.uro_building_detail_attribute_uro_total_floor_area xml_real64, uro_building_detail_attribute{}.uro_building_detail_attribute_uro_total_floor_area_units xml_buffer, uro_building_detail_attribute{}.uro_building_detail_attribute_uro_building_footprint_area xml_real64, uro_building_detail_attribute{}.uro_building_detail_attribute_uro_building_footprint_area_units xml_buffer, uro_building_detail_attribute{}.uro_building_detail_attribute_uro_building_roof_edge_area xml_real64, uro_building_detail_attribute{}.uro_building_detail_attribute_uro_building_roof_edge_area_units xml_buffer, uro_building_detail_attribute{}.uro_building_detail_attribute_uro_development_area xml_real64,
      uro_building_detail_attribute{}.uro_building_detail_attribute_uro_development_area_units xml_buffer, uro_building_detail_attribute{}.uro_building_detail_attribute_uro_building_structure_type xml_buffer, uro_building_detail_attribute{}.uro_building_detail_attribute_uro_building_structure_type_codeSpace xml_buffer, uro_building_detail_attribute{}.uro_building_detail_attribute_uro_building_structure_org_type xml_buffer, uro_building_detail_attribute{}.uro_building_detail_attribute_uro_building_structure_org_type_codeSpace xml_buffer, uro_building_detail_attribute{}.uro_building_detail_attribute_uro_fireproof_structure_type xml_buffer, uro_building_detail_attribute{}.uro_building_detail_attribute_uro_fireproof_structure_type_codeSpace xml_buffer, uro_building_detail_attribute{}.uro_building_detail_attribute_uro_implementing_body xml_buffer, uro_building_detail_attribute{}.uro_building_detail_attribute_uro_urban_plan_type xml_buffer, uro_building_detail_attribute{}.uro_building_detail_attribute_uro_urban_plan_type_codeSpace xml_buffer, uro_building_detail_attribute{}.uro_building_detail_attribute_uro_area_classification_type xml_buffer, uro_building_detail_attribute{}.uro_building_detail_attribute_uro_area_classification_type_codeSpace xml_buffer, uro_building_detail_attribute{}.uro_building_detail_attribute_uro_districts_and_zones_type{} xml_buffer, uro_building_detail_attribute{}.uro_building_detail_attribute_uro_districts_and_zones_type{}.codeSpace xml_buffer, uro_building_detail_attribute{}.uro_building_detail_attribute_uro_land_use_type xml_buffer, uro_building_detail_attribute{}.uro_building_detail_attribute_uro_land_use_type_codeSpace xml_buffer, uro_building_detail_attribute{}.uro_building_detail_attribute_uro_reference xml_buffer, uro_building_detail_attribute{}.uro_building_detail_attribute_uro_major_usage xml_buffer, uro_building_detail_attribute{}.uro_building_detail_attribute_uro_major_usage_codeSpace xml_buffer, uro_building_detail_attribute{}.uro_building_detail_attribute_uro_major_usage2 xml_buffer, uro_building_detail_attribute{}.uro_building_detail_attribute_uro_major_usage2_codeSpace xml_buffer, uro_building_detail_attribute{}.uro_building_detail_attribute_uro_org_usage xml_buffer, uro_building_detail_attribute{}.uro_building_detail_attribute_uro_org_usage_codeSpace xml_buffer, uro_building_detail_attribute{}.uro_building_detail_attribute_uro_org_usage2 xml_buffer, uro_building_detail_attribute{}.uro_building_detail_attribute_uro_org_usage2_codeSpace xml_buffer, uro_building_detail_attribute{}.uro_building_detail_attribute_uro_detailed_usage xml_buffer, uro_building_detail_attribute{}.uro_building_detail_attribute_uro_detailed_usage_codeSpace xml_buffer, uro_building_detail_attribute{}.uro_building_detail_attribute_uro_detailed_usage2 xml_buffer, uro_building_detail_attribute{}.uro_building_detail_attribute_uro_detailed_usage2_codeSpace xml_buffer, uro_building_detail_attribute{}.uro_building_detail_attribute_uro_detailed_usage3 xml_buffer,
      uro_building_detail_attribute{}.uro_building_detail_attribute_uro_detailed_usage3_codeSpace xml_buffer, uro_building_detail_attribute{}.uro_building_detail_attribute_uro_ground_floor_usage xml_buffer, uro_building_detail_attribute{}.uro_building_detail_attribute_uro_ground_floor_usage_codeSpace xml_buffer, uro_building_detail_attribute{}.uro_building_detail_attribute_uro_second_floor_usage xml_buffer, uro_building_detail_attribute{}.uro_building_detail_attribute_uro_second_floor_usage_codeSpace xml_buffer, uro_building_detail_attribute{}.uro_building_detail_attribute_uro_third_floor_usage xml_buffer, uro_building_detail_attribute{}.uro_building_detail_attribute_uro_third_floor_usage_codeSpace xml_buffer, uro_building_detail_attribute{}.uro_building_detail_attribute_uro_basement_usage xml_buffer, uro_building_detail_attribute{}.uro_building_detail_attribute_uro_basement_usage_codeSpace xml_buffer, uro_building_detail_attribute{}.uro_building_detail_attribute_uro_basement_first_usage xml_buffer, uro_building_detail_attribute{}.uro_building_detail_attribute_uro_basement_first_usage_codeSpace xml_buffer, uro_building_detail_attribute{}.uro_building_detail_attribute_uro_basement_second_usage xml_buffer, uro_building_detail_attribute{}.uro_building_detail_attribute_uro_basement_second_usage_codeSpace xml_buffer, uro_building_detail_attribute{}.uro_building_detail_attribute_uro_vacancy xml_buffer, uro_building_detail_attribute{}.uro_building_detail_attribute_uro_vacancy_codeSpace xml_buffer, uro_building_detail_attribute{}.uro_building_detail_attribute_uro_building_coverage_rate xml_real64, uro_building_detail_attribute{}.uro_building_detail_attribute_uro_floor_area_rate xml_real64, uro_building_detail_attribute{}.uro_building_detail_attribute_uro_specified_building_coverage_rate xml_real64, uro_building_detail_attribute{}.uro_building_detail_attribute_uro_specified_floor_area_rate xml_real64, uro_building_detail_attribute{}.uro_building_detail_attribute_uro_standard_floor_area_rate xml_real64, uro_building_detail_attribute{}.uro_building_detail_attribute_uro_building_height xml_real64, uro_building_detail_attribute{}.uro_building_detail_attribute_uro_building_height_units xml_buffer, uro_building_detail_attribute{}.uro_building_detail_attribute_uro_eave_height xml_real64, uro_building_detail_attribute{}.uro_building_detail_attribute_uro_eave_height_units xml_buffer, uro_building_detail_attribute{}.uro_building_detail_attribute_uro_note xml_buffer, uro_building_detail_attribute{}.uro_building_detail_attribute_uro_survey_year xml_buffer, uro_building_disaster_risk_attribute{}.uro_building_high_tide_risk_attribute_uro_description xml_buffer, uro_building_disaster_risk_attribute{}.uro_building_high_tide_risk_attribute_uro_description_codeSpace xml_buffer, uro_building_disaster_risk_attribute{}.uro_building_high_tide_risk_attribute_uro_rank xml_buffer, uro_building_disaster_risk_attribute{}.uro_building_high_tide_risk_attribute_uro_rank_codeSpace xml_buffer,
      uro_building_disaster_risk_attribute{}.uro_building_high_tide_risk_attribute_uro_rank_org xml_buffer, uro_building_disaster_risk_attribute{}.uro_building_high_tide_risk_attribute_uro_rank_org_codeSpace xml_buffer, uro_building_disaster_risk_attribute{}.uro_building_high_tide_risk_attribute_uro_depth xml_real64, uro_building_disaster_risk_attribute{}.uro_building_high_tide_risk_attribute_uro_depth_units xml_buffer, uro_building_disaster_risk_attribute{}.uro_building_inland_flooding_risk_attribute_uro_description xml_buffer, uro_building_disaster_risk_attribute{}.uro_building_inland_flooding_risk_attribute_uro_description_codeSpace xml_buffer, uro_building_disaster_risk_attribute{}.uro_building_inland_flooding_risk_attribute_uro_rank xml_buffer, uro_building_disaster_risk_attribute{}.uro_building_inland_flooding_risk_attribute_uro_rank_codeSpace xml_buffer, uro_building_disaster_risk_attribute{}.uro_building_inland_flooding_risk_attribute_uro_rank_org xml_buffer, uro_building_disaster_risk_attribute{}.uro_building_inland_flooding_risk_attribute_uro_rank_org_codeSpace xml_buffer, uro_building_disaster_risk_attribute{}.uro_building_inland_flooding_risk_attribute_uro_depth xml_real64, uro_building_disaster_risk_attribute{}.uro_building_inland_flooding_risk_attribute_uro_depth_units xml_buffer, uro_building_disaster_risk_attribute{}.uro_building_land_slide_risk_attribute_uro_description xml_buffer, uro_building_disaster_risk_attribute{}.uro_building_land_slide_risk_attribute_uro_description_codeSpace xml_buffer, uro_building_disaster_risk_attribute{}.uro_building_land_slide_risk_attribute_uro_area_type xml_buffer, uro_building_disaster_risk_attribute{}.uro_building_land_slide_risk_attribute_uro_area_type_codeSpace xml_buffer, uro_building_disaster_risk_attribute{}.uro_building_river_flooding_risk_attribute_uro_description xml_buffer, uro_building_disaster_risk_attribute{}.uro_building_river_flooding_risk_attribute_uro_description_codeSpace xml_buffer, uro_building_disaster_risk_attribute{}.uro_building_river_flooding_risk_attribute_uro_rank xml_buffer, uro_building_disaster_risk_attribute{}.uro_building_river_flooding_risk_attribute_uro_rank_codeSpace xml_buffer, uro_building_disaster_risk_attribute{}.uro_building_river_flooding_risk_attribute_uro_rank_org xml_buffer, uro_building_disaster_risk_attribute{}.uro_building_river_flooding_risk_attribute_uro_rank_org_codeSpace xml_buffer, uro_building_disaster_risk_attribute{}.uro_building_river_flooding_risk_attribute_uro_depth xml_real64, uro_building_disaster_risk_attribute{}.uro_building_river_flooding_risk_attribute_uro_depth_units xml_buffer, uro_building_disaster_risk_attribute{}.uro_building_river_flooding_risk_attribute_uro_admin_type xml_buffer, uro_building_disaster_risk_attribute{}.uro_building_river_flooding_risk_attribute_uro_admin_type_codeSpace xml_buffer, uro_building_disaster_risk_attribute{}.uro_building_river_flooding_risk_attribute_uro_scale xml_buffer, uro_building_disaster_risk_attribute{}.uro_building_river_flooding_risk_attribute_uro_scale_codeSpace xml_buffer, uro_building_disaster_risk_attribute{}.uro_building_river_flooding_risk_attribute_uro_duration xml_real64, uro_building_disaster_risk_attribute{}.uro_building_river_flooding_risk_attribute_uro_duration_units xml_buffer,
      uro_building_disaster_risk_attribute{}.uro_building_tsunami_risk_attribute_uro_description xml_buffer, uro_building_disaster_risk_attribute{}.uro_building_tsunami_risk_attribute_uro_description_codeSpace xml_buffer, uro_building_disaster_risk_attribute{}.uro_building_tsunami_risk_attribute_uro_rank xml_buffer, uro_building_disaster_risk_attribute{}.uro_building_tsunami_risk_attribute_uro_rank_codeSpace xml_buffer, uro_building_disaster_risk_attribute{}.uro_building_tsunami_risk_attribute_uro_rank_org xml_buffer, uro_building_disaster_risk_attribute{}.uro_building_tsunami_risk_attribute_uro_rank_org_codeSpace xml_buffer, uro_building_disaster_risk_attribute{}.uro_building_tsunami_risk_attribute_uro_depth xml_real64, uro_building_disaster_risk_attribute{}.uro_building_tsunami_risk_attribute_uro_depth_units xml_buffer, uro_building_idattribute{}.uro_building_idattribute_uro_building_id xml_buffer, uro_building_idattribute{}.uro_building_idattribute_uro_branch_id xml_int64, uro_building_idattribute{}.uro_building_idattribute_uro_part_id xml_int64, uro_building_idattribute{}.uro_building_idattribute_uro_prefecture xml_buffer, uro_building_idattribute{}.uro_building_idattribute_uro_prefecture_codeSpace xml_buffer, uro_building_idattribute{}.uro_building_idattribute_uro_city xml_buffer, uro_building_idattribute{}.uro_building_idattribute_uro_city_codeSpace xml_buffer, uro_key_value_pair_attribute{}.uro_key_value_pair_attribute_uro_key xml_buffer, uro_key_value_pair_attribute{}.uro_key_value_pair_attribute_uro_key_codeSpace xml_buffer, uro_key_value_pair_attribute{}.uro_key_value_pair_attribute_uro_code_value xml_buffer, uro_key_value_pair_attribute{}.uro_key_value_pair_attribute_uro_code_value_codeSpace xml_buffer, uro_key_value_pair_attribute{}.uro_key_value_pair_attribute_uro_string_value xml_buffer, uro_key_value_pair_attribute{}.uro_key_value_pair_attribute_uro_int_value xml_int64, uro_key_value_pair_attribute{}.uro_key_value_pair_attribute_uro_double_value xml_real64, uro_key_value_pair_attribute{}.uro_key_value_pair_attribute_uro_measured_value xml_real64, uro_key_value_pair_attribute{}.uro_key_value_pair_attribute_uro_measured_value_units xml_buffer, uro_key_value_pair_attribute{}.uro_key_value_pair_attribute_uro_date_value xml_date, uro_key_value_pair_attribute{}.uro_key_value_pair_attribute_uro_uri_value xml_buffer, uro_large_customer_facility_attribute{}.uro_large_customer_facility_attribute_uro_class xml_buffer, uro_large_customer_facility_attribute{}.uro_large_customer_facility_attribute_uro_class_codeSpace xml_buffer, uro_large_customer_facility_attribute{}.uro_large_customer_facility_attribute_uro_name xml_buffer, uro_large_customer_facility_attribute{}.uro_large_customer_facility_attribute_uro_capacity xml_int64,
      uro_large_customer_facility_attribute{}.uro_large_customer_facility_attribute_uro_owner xml_buffer, uro_large_customer_facility_attribute{}.uro_large_customer_facility_attribute_uro_total_floor_area xml_real64, uro_large_customer_facility_attribute{}.uro_large_customer_facility_attribute_uro_total_floor_area_units xml_buffer, uro_large_customer_facility_attribute{}.uro_large_customer_facility_attribute_uro_total_store_floor_area xml_real64, uro_large_customer_facility_attribute{}.uro_large_customer_facility_attribute_uro_total_store_floor_area_units xml_buffer, uro_large_customer_facility_attribute{}.uro_large_customer_facility_attribute_uro_inaugural_date xml_date, uro_large_customer_facility_attribute{}.uro_large_customer_facility_attribute_uro_key_tenants xml_buffer, uro_large_customer_facility_attribute{}.uro_large_customer_facility_attribute_uro_availability xml_boolean, uro_large_customer_facility_attribute{}.uro_large_customer_facility_attribute_uro_urban_plan_type xml_buffer, uro_large_customer_facility_attribute{}.uro_large_customer_facility_attribute_uro_urban_plan_type_codeSpace xml_buffer, uro_large_customer_facility_attribute{}.uro_large_customer_facility_attribute_uro_area_classification_type xml_buffer, uro_large_customer_facility_attribute{}.uro_large_customer_facility_attribute_uro_area_classification_type_codeSpace xml_buffer, uro_large_customer_facility_attribute{}.uro_large_customer_facility_attribute_uro_districts_and_zones_type{} xml_buffer, uro_large_customer_facility_attribute{}.uro_large_customer_facility_attribute_uro_districts_and_zones_type{}.codeSpace xml_buffer, uro_large_customer_facility_attribute{}.uro_large_customer_facility_attribute_uro_land_use_type xml_buffer, uro_large_customer_facility_attribute{}.uro_large_customer_facility_attribute_uro_land_use_type_codeSpace xml_buffer, uro_large_customer_facility_attribute{}.uro_large_customer_facility_attribute_uro_reference xml_buffer, uro_large_customer_facility_attribute{}.uro_large_customer_facility_attribute_uro_note xml_buffer, uro_large_customer_facility_attribute{}.uro_large_customer_facility_attribute_uro_survey_year xml_buffer
    -> FeatureJoiner_Building [LEFT]

Bookmark: FileGeoDatabase 建物データ
lod2_ClosureSurface (writer GEODATABASE_FILE_1)
    attributes: bldg_ClosureSurface_gml_id char(50), gml_description char(50), gml_name char(50), core_creationDate char(10), core_terminationDate char(10), bldg_Building_gml_id char(50)
lod3_ClosureSurface (writer GEODATABASE_FILE_1)
    attributes: bldg_ClosureSurface_gml_id char(50), gml_description char(50), gml_name char(50), core_creationDate char(10), core_terminationDate char(10), bldg_Building_gml_id char(50)
lod2_BuildingInstallation (writer GEODATABASE_FILE_1)
    attributes: bldg_BuildingInstallation_gml_id char(50), gml_description char(50), gml_name char(50), core_creationDate char(10), core_terminationDate char(10), bldg_class char(10), bldg_function char(10), bldg_Building_gml_id char(50)
lod3_BuildingInstallation (writer GEODATABASE_FILE_1)
    attributes: bldg_BuildingInstallation_gml_id char(50), gml_description char(50), gml_name char(50), core_creationDate char(10), core_terminationDate char(10), bldg_class char(10), bldg_function char(10), bldg_Building_gml_id char(50)
lod3_Window (writer GEODATABASE_FILE_1)
    attributes: bldg_Window_gml_id char(50), gml_description char(50), gml_name char(50), core_creationDate char(10), core_terminationDate char(10), bldg_Building_gml_id char(50)
lod2_WallSurface (writer GEODATABASE_FILE_1)
    attributes: bldg_WallSurface_gml_id char(50), gml_description char(50), gml_name char(50), core_creationDate char(10), core_terminationDate char(10), bldg_Building_gml_id char(50)
lod3_WallSurface (writer GEODATABASE_FILE_1)
    attributes: bldg_WallSurface_gml_id char(50), gml_description char(50), gml_name char(50), core_creationDate char(10), core_terminationDate char(10), bldg_Building_gml_id char(50)
lod2_RoofSurface (writer GEODATABASE_FILE_1)
    attributes: bldg_RoofSurface_gml_id char(50), gml_description char(50), gml_name char(50), core_creationDate char(10), core_terminationDate char(10), bldg_Building_gml_id char(50)
lod3_RoofSurface (writer GEODATABASE_FILE_1)
    attributes: bldg_RoofSurface_gml_id char(50), gml_description char(50), gml_name char(50), core_creationDate char(10), core_terminationDate char(10), bldg_Building_gml_id char(50)
lod2_OuterFloorSurface (writer GEODATABASE_FILE_1)
    attributes: bldg_OuterFloorSurface_gml_id char(50), gml_description char(50), gml_name char(50), core_creationDate char(10), core_terminationDate char(10), bldg_Building_gml_id char(50)
lod3_OuterFloorSurface (writer GEODATABASE_FILE_1)
    attributes: bldg_OuterFloorSurface_gml_id char(50), gml_description char(50), gml_name char(50), core_creationDate char(10), core_terminationDate char(10), bldg_Building_gml_id char(50)
lod3_OuterCeilingSurface (writer GEODATABASE_FILE_1)
    attributes: bldg_OuterCeilingSurface_gml_id char(50), gml_description char(50), gml_name char(50), core_creationDate char(10), core_terminationDate char(10), bldg_Building_gml_id char(50)
lod2_GroundSurface (writer GEODATABASE_FILE_1)
    attributes: bldg_GroundSurface_gml_id char(50), gml_description char(50), gml_name char(50), core_creationDate char(10), core_terminationDate char(10), bldg_Building_gml_id char(50)
lod3_GroundSurface (writer GEODATABASE_FILE_1)
    attributes: bldg_GroundSurface_gml_id char(50), gml_description char(50), gml_name char(50), core_creationDate char(10), core_terminationDate char(10), bldg_Building_gml_id char(50)
lod3_Door (writer GEODATABASE_FILE_1)
    attributes: bldg_Door_gml_id char(50), gml_description char(50), gml_name char(50), core_creationDate char(10), core_terminationDate char(10), bldg_Building_gml_id char(50)
lod2_BuildingPart (writer GEODATABASE_FILE_1)
    attributes: bldg_BuildingPart_gml_id char(50), gml_description char(50), gml_name char(50), core_creationDate char(10), core_terminationDate char(10), bldg_class char(10), bldg_usage1 char(10), bldg_usage2 char(10), bldg_usage3 char(10), bldg_usage4 char(10), bldg_usage5 char(10), bldg_usage6 char(10), bldg_usage7 char(10), bldg_usage8 char(10), bldg_usage9 char(10), bldg_usage10 char(10), bldg_yearOfConstruction char(10), bldg_yearOfDemolition char(10), bldg_roofType char(10), bldg_measuredHeight double, bldg_storeysAboveGround integer, bldg_storeysBelowGround integer, bldg_storeyHeightsAboveGround double, bldg_storeyHeightsBelowGround double, bldg_address char(50), uro_buildingIDAttribute_buildingID char(50), uro_buildingIDAttribute_branchID integer, uro_buildingIDAttribute_partID integer, uro_buildingIDAttribute_prefecture char(50), uro_buildingIDAttribute_city char(50),
      uro_BuildingDetailAttribute_serialNumberOfBuildingCertification char(50), uro_BuildingDetailAttribute_siteArea double, uro_BuildingDetailAttribute_totalFloorArea double, uro_BuildingDetailAttribute_buildingFootprintArea double, uro_BuildingDetailAttribute_buildingRoofEdgeArea double, uro_BuildingDetailAttribute_developmentArea double, uro_BuildingDetailAttribute_buildingStructureType char(10), uro_BuildingDetailAttribute_buildingStructureOrgType char(10), uro_BuildingDetailAttribute_fireproofStructureType char(10), uro_BuildingDetailAttribute_implementingBody char(50), uro_BuildingDetailAttribute_urbanPlanType char(10), uro_BuildingDetailAttribute_areaClassificationType char(10), uro_BuildingDetailAttribute_districtsAndZonesType1 char(10), uro_BuildingDetailAttribute_districtsAndZonesType2 char(10), uro_BuildingDetailAttribute_districtsAndZonesType3 char(10), uro_BuildingDetailAttribute_districtsAndZonesType4 char(10), uro_BuildingDetailAttribute_districtsAndZonesType5 char(10), uro_BuildingDetailAttribute_districtsAndZonesType6 char(10), uro_BuildingDetailAttribute_districtsAndZonesType7 char(10), uro_BuildingDetailAttribute_districtsAndZonesType8 char(10), uro_BuildingDetailAttribute_districtsAndZonesType9 char(10), uro_BuildingDetailAttribute_districtsAndZonesType10 char(10), uro_BuildingDetailAttribute_landUseType char(10), uro_BuildingDetailAttribute_reference char(10), uro_BuildingDetailAttribute_majorUsage char(10), uro_BuildingDetailAttribute_majorUsage2 char(10), uro_BuildingDetailAttribute_orgUsage char(10), uro_BuildingDetailAttribute_orgUsage2 char(10), uro_BuildingDetailAttribute_detailedUsage char(10), uro_BuildingDetailAttribute_detailedUsage2 char(10),
      uro_BuildingDetailAttribute_detailedUsage3 char(10), uro_BuildingDetailAttribute_groundFloorUsage char(10), uro_BuildingDetailAttribute_secondFloorUsage char(10), uro_BuildingDetailAttribute_thirdFloorUsage char(10), uro_BuildingDetailAttribute_basementUsage char(10), uro_BuildingDetailAttribute_basementFirstUsage char(10), uro_BuildingDetailAttribute_basementSecondUsage char(10), uro_BuildingDetailAttribute_vacancy char(10), uro_BuildingDetailAttribute_buildingCoverageRate double, uro_BuildingDetailAttribute_floorAreaRate double, uro_BuildingDetailAttribute_specifiedBuildingCoverageRate double, uro_BuildingDetailAttribute_specifiedFloorAreaRate double, uro_BuildingDetailAttribute_standardFloorAreaRate double, uro_BuildingDetailAttribute_buildingHeight double, uro_BuildingDetailAttribute_eaveHeight double, uro_BuildingDetailAttribute_note char(50), uro_BuildingDetailAttribute_surveyYear char(10), bldg_Building_gml_id char(50), xml_genericAttributeSet char(10000)
lod3_BuildingPart (writer GEODATABASE_FILE_1)
    attributes: bldg_BuildingPart_gml_id char(50), gml_description char(50), gml_name char(50), core_creationDate char(10), core_terminationDate char(10), bldg_class char(10), bldg_usage1 char(10), bldg_usage2 char(10), bldg_usage3 char(10), bldg_usage4 char(10), bldg_usage5 char(10), bldg_usage6 char(10), bldg_usage7 char(10), bldg_usage8 char(10), bldg_usage9 char(10), bldg_usage10 char(10), bldg_yearOfConstruction char(10), bldg_yearOfDemolition char(10), bldg_roofType char(10), bldg_measuredHeight double, bldg_storeysAboveGround integer, bldg_storeysBelowGround integer, bldg_storeyHeightsAboveGround double, bldg_storeyHeightsBelowGround double, bldg_address char(50), uro_buildingIDAttribute_buildingID char(50), uro_buildingIDAttribute_branchID integer, uro_buildingIDAttribute_partID integer, uro_buildingIDAttribute_prefecture char(50), uro_buildingIDAttribute_city char(50),
      uro_BuildingDetailAttribute_serialNumberOfBuildingCertification char(50), uro_BuildingDetailAttribute_siteArea double, uro_BuildingDetailAttribute_totalFloorArea double, uro_BuildingDetailAttribute_buildingFootprintArea double, uro_BuildingDetailAttribute_buildingRoofEdgeArea double, uro_BuildingDetailAttribute_developmentArea double, uro_BuildingDetailAttribute_buildingStructureType char(10), uro_BuildingDetailAttribute_buildingStructureOrgType char(10), uro_BuildingDetailAttribute_fireproofStructureType char(10), uro_BuildingDetailAttribute_implementingBody char(50), uro_BuildingDetailAttribute_urbanPlanType char(10), uro_BuildingDetailAttribute_areaClassificationType char(10), uro_BuildingDetailAttribute_districtsAndZonesType1 char(10), uro_BuildingDetailAttribute_districtsAndZonesType2 char(10), uro_BuildingDetailAttribute_districtsAndZonesType3 char(10), uro_BuildingDetailAttribute_districtsAndZonesType4 char(10), uro_BuildingDetailAttribute_districtsAndZonesType5 char(10), uro_BuildingDetailAttribute_districtsAndZonesType6 char(10), uro_BuildingDetailAttribute_districtsAndZonesType7 char(10), uro_BuildingDetailAttribute_districtsAndZonesType8 char(10), uro_BuildingDetailAttribute_districtsAndZonesType9 char(10), uro_BuildingDetailAttribute_districtsAndZonesType10 char(10), uro_BuildingDetailAttribute_landUseType char(10), uro_BuildingDetailAttribute_reference char(10), uro_BuildingDetailAttribute_majorUsage char(10), uro_BuildingDetailAttribute_majorUsage2 char(10), uro_BuildingDetailAttribute_orgUsage char(10), uro_BuildingDetailAttribute_orgUsage2 char(10), uro_BuildingDetailAttribute_detailedUsage char(10), uro_BuildingDetailAttribute_detailedUsage2 char(10),
      uro_BuildingDetailAttribute_detailedUsage3 char(10), uro_BuildingDetailAttribute_groundFloorUsage char(10), uro_BuildingDetailAttribute_secondFloorUsage char(10), uro_BuildingDetailAttribute_thirdFloorUsage char(10), uro_BuildingDetailAttribute_basementUsage char(10), uro_BuildingDetailAttribute_basementFirstUsage char(10), uro_BuildingDetailAttribute_basementSecondUsage char(10), uro_BuildingDetailAttribute_vacancy char(10), uro_BuildingDetailAttribute_buildingCoverageRate double, uro_BuildingDetailAttribute_floorAreaRate double, uro_BuildingDetailAttribute_specifiedBuildingCoverageRate double, uro_BuildingDetailAttribute_specifiedFloorAreaRate double, uro_BuildingDetailAttribute_standardFloorAreaRate double, uro_BuildingDetailAttribute_buildingHeight double, uro_BuildingDetailAttribute_eaveHeight double, uro_BuildingDetailAttribute_note char(50), uro_BuildingDetailAttribute_surveyYear char(10), bldg_Building_gml_id char(50), xml_genericAttributeSet char(10000)
lod0_Building (writer GEODATABASE_FILE_1)
    attributes: bldg_Building_gml_id char(50), gml_description char(50), gml_name char(50), core_creationDate char(10), core_terminationDate char(10), bldg_class char(10), bldg_usage1 char(10), bldg_usage2 char(10), bldg_usage3 char(10), bldg_usage4 char(10), bldg_usage5 char(10), bldg_usage6 char(10), bldg_usage7 char(10), bldg_usage8 char(10), bldg_usage9 char(10), bldg_usage10 char(10), bldg_yearOfConstruction char(10), bldg_yearOfDemolition char(10), bldg_roofType char(10), bldg_measuredHeight double, bldg_storeysAboveGround integer, bldg_storeysBelowGround integer, bldg_storeyHeightsAboveGround double, bldg_storeyHeightsBelowGround double, bldg_address char(50), uro_buildingIDAttribute_buildingID char(50), uro_buildingIDAttribute_partID integer, uro_buildingIDAttribute_prefecture char(50), uro_buildingIDAttribute_city char(50), uro_BuildingDetailAttribute_serialNumberOfBuildingCertification char(50),
      uro_BuildingDetailAttribute_siteArea double, uro_BuildingDetailAttribute_totalFloorArea double, uro_BuildingDetailAttribute_buildingFootprintArea double, uro_BuildingDetailAttribute_buildingRoofEdgeArea double, uro_BuildingDetailAttribute_developmentArea double, uro_BuildingDetailAttribute_buildingStructureType char(10), uro_BuildingDetailAttribute_buildingStructureOrgType char(10), uro_BuildingDetailAttribute_fireproofStructureType char(10), uro_BuildingDetailAttribute_implementingBody char(50), uro_BuildingDetailAttribute_urbanPlanType char(10), uro_BuildingDetailAttribute_areaClassificationType char(10), uro_BuildingDetailAttribute_districtsAndZonesType1 char(10), uro_BuildingDetailAttribute_districtsAndZonesType2 char(10), uro_BuildingDetailAttribute_districtsAndZonesType3 char(10), uro_BuildingDetailAttribute_districtsAndZonesType4 char(10), uro_BuildingDetailAttribute_districtsAndZonesType5 char(10), uro_BuildingDetailAttribute_districtsAndZonesType6 char(10), uro_BuildingDetailAttribute_districtsAndZonesType7 char(10), uro_BuildingDetailAttribute_districtsAndZonesType8 char(10), uro_BuildingDetailAttribute_districtsAndZonesType9 char(10), uro_BuildingDetailAttribute_districtsAndZonesType10 char(10), uro_BuildingDetailAttribute_landUseType char(10), uro_BuildingDetailAttribute_reference char(10), uro_BuildingDetailAttribute_majorUsage char(10), uro_BuildingDetailAttribute_majorUsage2 char(10), uro_BuildingDetailAttribute_orgUsage char(10), uro_BuildingDetailAttribute_orgUsage2 char(10), uro_BuildingDetailAttribute_detailedUsage char(10), uro_BuildingDetailAttribute_detailedUsage2 char(10), uro_BuildingDetailAttribute_detailedUsage3 char(10),
      uro_BuildingDetailAttribute_groundFloorUsage char(10), uro_BuildingDetailAttribute_secondFloorUsage char(10), uro_BuildingDetailAttribute_thirdFloorUsage char(10), uro_BuildingDetailAttribute_basementUsage char(10), uro_BuildingDetailAttribute_basementFirstUsage char(10), uro_BuildingDetailAttribute_basementSecondUsage char(10), uro_BuildingDetailAttribute_vacancy char(10), uro_BuildingDetailAttribute_buildingCoverageRate double, uro_BuildingDetailAttribute_floorAreaRate double, uro_BuildingDetailAttribute_specifiedBuildingCoverageRate double, uro_BuildingDetailAttribute_specifiedFloorAreaRate double, uro_BuildingDetailAttribute_standardFloorAreaRate double, uro_BuildingDetailAttribute_buildingHeight double, uro_BuildingDetailAttribute_eaveHeight double, uro_BuildingDetailAttribute_note char(50), uro_BuildingDetailAttribute_surveyYear char(10), uro_LargeCustomerFacilityAttribute_class char(10), uro_LargeCustomerFacilityAttribute_name char(50), uro_LargeCustomerFacilityAttribute_capacity integer, uro_LargeCustomerFacilityAttribute_owner char(50), uro_LargeCustomerFacilityAttribute_totalFloorArea double, uro_LargeCustomerFacilityAttribute_totalStoreFloorArea double, uro_LargeCustomerFacilityAttribute_inauguralDate char(10), uro_LargeCustomerFacilityAttribute_keyTenants char(50), uro_LargeCustomerFacilityAttribute_availability char(5), uro_LargeCustomerFacilityAttribute_urbanPlanType char(5), uro_LargeCustomerFacilityAttribute_areaClassificationType char(10), uro_LargeCustomerFacilityAttribute_districtsAndZonesType1 char(10), uro_LargeCustomerFacilityAttribute_districtsAndZonesType2 char(10), uro_LargeCustomerFacilityAttribute_districtsAndZonesType3 char(10),
      uro_LargeCustomerFacilityAttribute_districtsAndZonesType4 char(10), uro_LargeCustomerFacilityAttribute_districtsAndZonesType5 char(10), uro_LargeCustomerFacilityAttribute_districtsAndZonesType6 char(10), uro_LargeCustomerFacilityAttribute_districtsAndZonesType7 char(10), uro_LargeCustomerFacilityAttribute_districtsAndZonesType8 char(10), uro_LargeCustomerFacilityAttribute_districtsAndZonesType9 char(10), uro_LargeCustomerFacilityAttribute_districtsAndZonesType10 char(10), uro_LargeCustomerFacilityAttribute_landUseType char(10), uro_LargeCustomerFacilityAttribute_reference char(50), uro_LargeCustomerFacilityAttribute_note char(50), uro_LargeCustomerFacilityAttribute_surveyYear char(10), uro_BuildingRiverFloodingRiskAttribute_description char(10), uro_BuildingRiverFloodingRiskAttribute_rank char(10), uro_BuildingRiverFloodingRiskAttribute_rankOrg char(10), uro_BuildingRiverFloodingRiskAttribute_depth double, uro_BuildingRiverFloodingRiskAttribute_adminType char(10), uro_BuildingRiverFloodingRiskAttribute_scale char(10), uro_BuildingRiverFloodingRiskAttribute_duration double, uro_BuildingTsunamiRiskAttribute_description char(10), uro_BuildingTsunamiRiskAttribute_rank char(10), uro_BuildingTsunamiRiskAttribute_rankOrg char(10), uro_BuildingTsunamiRiskAttribute_depth double, uro_BuildingHighTideRiskAttribute_description char(10), uro_BuildingHighTideRiskAttribute_rank char(10), uro_BuildingHighTideRiskAttribute_rankOrg char(10), uro_BuildingHighTideRiskAttribute_depth double, uro_BuildingInlandFloodingRiskAttribute_description char(10), uro_BuildingInlandFloodingRiskAttribute_rank char(10), uro_BuildingInlandFloodingRiskAttribute_rankOrg char(10), uro_BuildingInlandFloodingRiskAttribute_depth double,
      uro_BuildingLandSlideRiskAttribute_description1 char(10), uro_BuildingLandSlideRiskAttribute_areaType1 char(10), uro_BuildingLandSlideRiskAttribute_description2 char(10), uro_BuildingLandSlideRiskAttribute_areaType2 char(10), uro_BuildingLandSlideRiskAttribute_description3 char(10), uro_BuildingLandSlideRiskAttribute_areaType3 char(10), uro_KeyValuePairAttribute_key1 char(10), uro_KeyValuePairAttribute_codeValue1 char(10), uro_KeyValuePairAttribute_key2 char(10), uro_KeyValuePairAttribute_codeValue2 char(10), uro_KeyValuePairAttribute_key3 char(10), uro_KeyValuePairAttribute_codeValue3 char(10), uro_KeyValuePairAttribute_key4 char(10), uro_KeyValuePairAttribute_codeValue4 char(10), uro_KeyValuePairAttribute_key5 char(10), uro_KeyValuePairAttribute_codeValue5 char(10), uro_KeyValuePairAttribute_key6 char(10), uro_KeyValuePairAttribute_codeValue6 char(10), uro_KeyValuePairAttribute_key7 char(10), uro_KeyValuePairAttribute_codeValue7 char(10), uro_KeyValuePairAttribute_key8 char(10), uro_KeyValuePairAttribute_codeValue8 char(10), uro_KeyValuePairAttribute_key9 char(10), uro_KeyValuePairAttribute_codeValue9 char(10), uro_KeyValuePairAttribute_key10 char(10), uro_KeyValuePairAttribute_codeValue10 char(10), uro_BuildingDataQualityAttribute_srcScale1 char(10), uro_BuildingDataQualityAttribute_srcScale2 char(10), uro_BuildingDataQualityAttribute_srcScale3 char(10), uro_BuildingDataQualityAttribute_srcScale4 char(10),
      uro_BuildingDataQualityAttribute_srcScale5 char(10), uro_BuildingDataQualityAttribute_srcScale6 char(10), uro_BuildingDataQualityAttribute_srcScale7 char(10), uro_BuildingDataQualityAttribute_srcScale8 char(10), uro_BuildingDataQualityAttribute_srcScale9 char(10), uro_BuildingDataQualityAttribute_srcScale10 char(10), uro_BuildingDataQualityAttribute_geometrySrcDesc1 char(10), uro_BuildingDataQualityAttribute_geometrySrcDesc2 char(10), uro_BuildingDataQualityAttribute_geometrySrcDesc3 char(10), uro_BuildingDataQualityAttribute_geometrySrcDesc4 char(10), uro_BuildingDataQualityAttribute_geometrySrcDesc5 char(10), uro_BuildingDataQualityAttribute_geometrySrcDesc6 char(10), uro_BuildingDataQualityAttribute_geometrySrcDesc7 char(10), uro_BuildingDataQualityAttribute_geometrySrcDesc8 char(10), uro_BuildingDataQualityAttribute_geometrySrcDesc9 char(10), uro_BuildingDataQualityAttribute_geometrySrcDesc10 char(10), uro_BuildingDataQualityAttribute_thematicSrcDesc1 char(10), uro_BuildingDataQualityAttribute_thematicSrcDesc2 char(10), uro_BuildingDataQualityAttribute_thematicSrcDesc3 char(10), uro_BuildingDataQualityAttribute_thematicSrcDesc4 char(10), uro_BuildingDataQualityAttribute_thematicSrcDesc5 char(10), uro_BuildingDataQualityAttribute_thematicSrcDesc6 char(10), uro_BuildingDataQualityAttribute_thematicSrcDesc7 char(10), uro_BuildingDataQualityAttribute_thematicSrcDesc8 char(10), uro_BuildingDataQualityAttribute_thematicSrcDesc9 char(10), uro_BuildingDataQualityAttribute_thematicSrcDesc10 char(10), uro_BuildingDataQualityAttribute_appearanceSrcDesc1 char(10), uro_BuildingDataQualityAttribute_appearanceSrcDesc2 char(10), uro_BuildingDataQualityAttribute_appearanceSrcDesc3 char(10), uro_BuildingDataQualityAttribute_appearanceSrcDesc4 char(10),
      uro_BuildingDataQualityAttribute_appearanceSrcDesc5 char(10), uro_BuildingDataQualityAttribute_appearanceSrcDesc6 char(10), uro_BuildingDataQualityAttribute_appearanceSrcDesc7 char(10), uro_BuildingDataQualityAttribute_appearanceSrcDesc8 char(10), uro_BuildingDataQualityAttribute_appearanceSrcDesc9 char(10), uro_BuildingDataQualityAttribute_appearanceSrcDesc10 char(10), uro_BuildingDataQualityAttribute_lod1HeightType char(10), uro_BuildingDataQualityAttribute_lodType1 char(10), uro_BuildingDataQualityAttribute_lodType2 char(10), uro_BuildingDataQualityAttribute_lodType3 char(10), xml_genericAttributeSet char(10000)
lod1_Building (writer GEODATABASE_FILE_1)
    attributes: bldg_Building_gml_id char(50), gml_description char(50), gml_name char(50), core_creationDate char(10), core_terminationDate char(10), bldg_class char(10), bldg_usage1 char(10), bldg_usage2 char(10), bldg_usage3 char(10), bldg_usage4 char(10), bldg_usage5 char(10), bldg_usage6 char(10), bldg_usage7 char(10), bldg_usage8 char(10), bldg_usage9 char(10), bldg_usage10 char(10), bldg_yearOfConstruction char(10), bldg_yearOfDemolition char(10), bldg_roofType char(10), bldg_measuredHeight double, bldg_storeysAboveGround integer, bldg_storeysBelowGround integer, bldg_storeyHeightsAboveGround double, bldg_storeyHeightsBelowGround double, bldg_address char(50), uro_buildingIDAttribute_buildingID char(50), uro_buildingIDAttribute_partID integer, uro_buildingIDAttribute_prefecture char(50), uro_buildingIDAttribute_city char(50), uro_BuildingDetailAttribute_serialNumberOfBuildingCertification char(50),
      uro_BuildingDetailAttribute_siteArea double, uro_BuildingDetailAttribute_totalFloorArea double, uro_BuildingDetailAttribute_buildingFootprintArea double, uro_BuildingDetailAttribute_buildingRoofEdgeArea double, uro_BuildingDetailAttribute_developmentArea double, uro_BuildingDetailAttribute_buildingStructureType char(10), uro_BuildingDetailAttribute_buildingStructureOrgType char(10), uro_BuildingDetailAttribute_fireproofStructureType char(10), uro_BuildingDetailAttribute_implementingBody char(50), uro_BuildingDetailAttribute_urbanPlanType char(10), uro_BuildingDetailAttribute_areaClassificationType char(10), uro_BuildingDetailAttribute_districtsAndZonesType1 char(10), uro_BuildingDetailAttribute_districtsAndZonesType2 char(10), uro_BuildingDetailAttribute_districtsAndZonesType3 char(10), uro_BuildingDetailAttribute_districtsAndZonesType4 char(10), uro_BuildingDetailAttribute_districtsAndZonesType5 char(10), uro_BuildingDetailAttribute_districtsAndZonesType6 char(10), uro_BuildingDetailAttribute_districtsAndZonesType7 char(10), uro_BuildingDetailAttribute_districtsAndZonesType8 char(10), uro_BuildingDetailAttribute_districtsAndZonesType9 char(10), uro_BuildingDetailAttribute_districtsAndZonesType10 char(10), uro_BuildingDetailAttribute_landUseType char(10), uro_BuildingDetailAttribute_reference char(10), uro_BuildingDetailAttribute_majorUsage char(10), uro_BuildingDetailAttribute_majorUsage2 char(10), uro_BuildingDetailAttribute_orgUsage char(10), uro_BuildingDetailAttribute_orgUsage2 char(10), uro_BuildingDetailAttribute_detailedUsage char(10), uro_BuildingDetailAttribute_detailedUsage2 char(10), uro_BuildingDetailAttribute_detailedUsage3 char(10),
      uro_BuildingDetailAttribute_groundFloorUsage char(10), uro_BuildingDetailAttribute_secondFloorUsage char(10), uro_BuildingDetailAttribute_thirdFloorUsage char(10), uro_BuildingDetailAttribute_basementUsage char(10), uro_BuildingDetailAttribute_basementFirstUsage char(10), uro_BuildingDetailAttribute_basementSecondUsage char(10), uro_BuildingDetailAttribute_vacancy char(10), uro_BuildingDetailAttribute_buildingCoverageRate double, uro_BuildingDetailAttribute_floorAreaRate double, uro_BuildingDetailAttribute_specifiedBuildingCoverageRate double, uro_BuildingDetailAttribute_specifiedFloorAreaRate double, uro_BuildingDetailAttribute_standardFloorAreaRate double, uro_BuildingDetailAttribute_buildingHeight double, uro_BuildingDetailAttribute_eaveHeight double, uro_BuildingDetailAttribute_note char(50), uro_BuildingDetailAttribute_surveyYear char(10), uro_LargeCustomerFacilityAttribute_class char(10), uro_LargeCustomerFacilityAttribute_name char(50), uro_LargeCustomerFacilityAttribute_capacity integer, uro_LargeCustomerFacilityAttribute_owner char(50), uro_LargeCustomerFacilityAttribute_totalFloorArea double, uro_LargeCustomerFacilityAttribute_totalStoreFloorArea double, uro_LargeCustomerFacilityAttribute_inauguralDate char(10), uro_LargeCustomerFacilityAttribute_keyTenants char(50), uro_LargeCustomerFacilityAttribute_availability char(5), uro_LargeCustomerFacilityAttribute_urbanPlanType char(5), uro_LargeCustomerFacilityAttribute_areaClassificationType char(10), uro_LargeCustomerFacilityAttribute_districtsAndZonesType1 char(10), uro_LargeCustomerFacilityAttribute_districtsAndZonesType2 char(10), uro_LargeCustomerFacilityAttribute_districtsAndZonesType3 char(10),
      uro_LargeCustomerFacilityAttribute_districtsAndZonesType4 char(10), uro_LargeCustomerFacilityAttribute_districtsAndZonesType5 char(10), uro_LargeCustomerFacilityAttribute_districtsAndZonesType6 char(10), uro_LargeCustomerFacilityAttribute_districtsAndZonesType7 char(10), uro_LargeCustomerFacilityAttribute_districtsAndZonesType8 char(10), uro_LargeCustomerFacilityAttribute_districtsAndZonesType9 char(10), uro_LargeCustomerFacilityAttribute_districtsAndZonesType10 char(10), uro_LargeCustomerFacilityAttribute_landUseType char(10), uro_LargeCustomerFacilityAttribute_reference char(50), uro_LargeCustomerFacilityAttribute_note char(50), uro_LargeCustomerFacilityAttribute_surveyYear char(10), uro_BuildingRiverFloodingRiskAttribute_description char(10), uro_BuildingRiverFloodingRiskAttribute_rank char(10), uro_BuildingRiverFloodingRiskAttribute_rankOrg char(10), uro_BuildingRiverFloodingRiskAttribute_depth double, uro_BuildingRiverFloodingRiskAttribute_adminType char(10), uro_BuildingRiverFloodingRiskAttribute_scale char(10), uro_BuildingRiverFloodingRiskAttribute_duration double, uro_BuildingTsunamiRiskAttribute_description char(10), uro_BuildingTsunamiRiskAttribute_rank char(10), uro_BuildingTsunamiRiskAttribute_rankOrg char(10), uro_BuildingTsunamiRiskAttribute_depth double, uro_BuildingHighTideRiskAttribute_description char(10), uro_BuildingHighTideRiskAttribute_rank char(10), uro_BuildingHighTideRiskAttribute_rankOrg char(10), uro_BuildingHighTideRiskAttribute_depth double, uro_BuildingInlandFloodingRiskAttribute_description char(10), uro_BuildingInlandFloodingRiskAttribute_rank char(10), uro_BuildingInlandFloodingRiskAttribute_rankOrg char(10), uro_BuildingInlandFloodingRiskAttribute_depth double,
      uro_BuildingLandSlideRiskAttribute_description1 char(10), uro_BuildingLandSlideRiskAttribute_areaType1 char(10), uro_BuildingLandSlideRiskAttribute_description2 char(10), uro_BuildingLandSlideRiskAttribute_areaType2 char(10), uro_BuildingLandSlideRiskAttribute_description3 char(10), uro_BuildingLandSlideRiskAttribute_areaType3 char(10), uro_KeyValuePairAttribute_key1 char(10), uro_KeyValuePairAttribute_codeValue1 char(10), uro_KeyValuePairAttribute_key2 char(10), uro_KeyValuePairAttribute_codeValue2 char(10), uro_KeyValuePairAttribute_key3 char(10), uro_KeyValuePairAttribute_codeValue3 char(10), uro_KeyValuePairAttribute_key4 char(10), uro_KeyValuePairAttribute_codeValue4 char(10), uro_KeyValuePairAttribute_key5 char(10), uro_KeyValuePairAttribute_codeValue5 char(10), uro_KeyValuePairAttribute_key6 char(10), uro_KeyValuePairAttribute_codeValue6 char(10), uro_KeyValuePairAttribute_key7 char(10), uro_KeyValuePairAttribute_codeValue7 char(10), uro_KeyValuePairAttribute_key8 char(10), uro_KeyValuePairAttribute_codeValue8 char(10), uro_KeyValuePairAttribute_key9 char(10), uro_KeyValuePairAttribute_codeValue9 char(10), uro_KeyValuePairAttribute_key10 char(10), uro_KeyValuePairAttribute_codeValue10 char(10), uro_BuildingDataQualityAttribute_srcScale1 char(10), uro_BuildingDataQualityAttribute_srcScale2 char(10), uro_BuildingDataQualityAttribute_srcScale3 char(10), uro_BuildingDataQualityAttribute_srcScale4 char(10),
      uro_BuildingDataQualityAttribute_srcScale5 char(10), uro_BuildingDataQualityAttribute_srcScale6 char(10), uro_BuildingDataQualityAttribute_srcScale7 char(10), uro_BuildingDataQualityAttribute_srcScale8 char(10), uro_BuildingDataQualityAttribute_srcScale9 char(10), uro_BuildingDataQualityAttribute_srcScale10 char(10), uro_BuildingDataQualityAttribute_geometrySrcDesc1 char(10), uro_BuildingDataQualityAttribute_geometrySrcDesc2 char(10), uro_BuildingDataQualityAttribute_geometrySrcDesc3 char(10), uro_BuildingDataQualityAttribute_geometrySrcDesc4 char(10), uro_BuildingDataQualityAttribute_geometrySrcDesc5 char(10), uro_BuildingDataQualityAttribute_geometrySrcDesc6 char(10), uro_BuildingDataQualityAttribute_geometrySrcDesc7 char(10), uro_BuildingDataQualityAttribute_geometrySrcDesc8 char(10), uro_BuildingDataQualityAttribute_geometrySrcDesc9 char(10), uro_BuildingDataQualityAttribute_geometrySrcDesc10 char(10), uro_BuildingDataQualityAttribute_thematicSrcDesc1 char(10), uro_BuildingDataQualityAttribute_thematicSrcDesc2 char(10), uro_BuildingDataQualityAttribute_thematicSrcDesc3 char(10), uro_BuildingDataQualityAttribute_thematicSrcDesc4 char(10), uro_BuildingDataQualityAttribute_thematicSrcDesc5 char(10), uro_BuildingDataQualityAttribute_thematicSrcDesc6 char(10), uro_BuildingDataQualityAttribute_thematicSrcDesc7 char(10), uro_BuildingDataQualityAttribute_thematicSrcDesc8 char(10), uro_BuildingDataQualityAttribute_thematicSrcDesc9 char(10), uro_BuildingDataQualityAttribute_thematicSrcDesc10 char(10), uro_BuildingDataQualityAttribute_appearanceSrcDesc1 char(10), uro_BuildingDataQualityAttribute_appearanceSrcDesc2 char(10), uro_BuildingDataQualityAttribute_appearanceSrcDesc3 char(10), uro_BuildingDataQualityAttribute_appearanceSrcDesc4 char(10),
      uro_BuildingDataQualityAttribute_appearanceSrcDesc5 char(10), uro_BuildingDataQualityAttribute_appearanceSrcDesc6 char(10), uro_BuildingDataQualityAttribute_appearanceSrcDesc7 char(10), uro_BuildingDataQualityAttribute_appearanceSrcDesc8 char(10), uro_BuildingDataQualityAttribute_appearanceSrcDesc9 char(10), uro_BuildingDataQualityAttribute_appearanceSrcDesc10 char(10), uro_BuildingDataQualityAttribute_lod1HeightType char(10), uro_BuildingDataQualityAttribute_lodType1 char(10), uro_BuildingDataQualityAttribute_lodType2 char(10), uro_BuildingDataQualityAttribute_lodType3 char(10), xml_genericAttributeSet char(10000)
lod2_Building (writer GEODATABASE_FILE_1)
    attributes: bldg_Building_gml_id char(50), gml_description char(50), gml_name char(50), core_creationDate char(10), core_terminationDate char(10), bldg_class char(10), bldg_usage1 char(10), bldg_usage2 char(10), bldg_usage3 char(10), bldg_usage4 char(10), bldg_usage5 char(10), bldg_usage6 char(10), bldg_usage7 char(10), bldg_usage8 char(10), bldg_usage9 char(10), bldg_usage10 char(10), bldg_yearOfConstruction char(10), bldg_yearOfDemolition char(10), bldg_roofType char(10), bldg_measuredHeight double, bldg_storeysAboveGround integer, bldg_storeysBelowGround integer, bldg_storeyHeightsAboveGround double, bldg_storeyHeightsBelowGround double, bldg_address char(50), uro_buildingIDAttribute_buildingID char(50), uro_buildingIDAttribute_partID integer, uro_buildingIDAttribute_prefecture char(50), uro_buildingIDAttribute_city char(50), uro_BuildingDetailAttribute_serialNumberOfBuildingCertification char(50),
      uro_BuildingDetailAttribute_siteArea double, uro_BuildingDetailAttribute_totalFloorArea double, uro_BuildingDetailAttribute_buildingFootprintArea double, uro_BuildingDetailAttribute_buildingRoofEdgeArea double, uro_BuildingDetailAttribute_developmentArea double, uro_BuildingDetailAttribute_buildingStructureType char(10), uro_BuildingDetailAttribute_buildingStructureOrgType char(10), uro_BuildingDetailAttribute_fireproofStructureType char(10), uro_BuildingDetailAttribute_implementingBody char(50), uro_BuildingDetailAttribute_urbanPlanType char(10), uro_BuildingDetailAttribute_areaClassificationType char(10), uro_BuildingDetailAttribute_districtsAndZonesType1 char(10), uro_BuildingDetailAttribute_districtsAndZonesType2 char(10), uro_BuildingDetailAttribute_districtsAndZonesType3 char(10), uro_BuildingDetailAttribute_districtsAndZonesType4 char(10), uro_BuildingDetailAttribute_districtsAndZonesType5 char(10), uro_BuildingDetailAttribute_districtsAndZonesType6 char(10), uro_BuildingDetailAttribute_districtsAndZonesType7 char(10), uro_BuildingDetailAttribute_districtsAndZonesType8 char(10), uro_BuildingDetailAttribute_districtsAndZonesType9 char(10), uro_BuildingDetailAttribute_districtsAndZonesType10 char(10), uro_BuildingDetailAttribute_landUseType char(10), uro_BuildingDetailAttribute_reference char(10), uro_BuildingDetailAttribute_majorUsage char(10), uro_BuildingDetailAttribute_majorUsage2 char(10), uro_BuildingDetailAttribute_orgUsage char(10), uro_BuildingDetailAttribute_orgUsage2 char(10), uro_BuildingDetailAttribute_detailedUsage char(10), uro_BuildingDetailAttribute_detailedUsage2 char(10), uro_BuildingDetailAttribute_detailedUsage3 char(10),
      uro_BuildingDetailAttribute_groundFloorUsage char(10), uro_BuildingDetailAttribute_secondFloorUsage char(10), uro_BuildingDetailAttribute_thirdFloorUsage char(10), uro_BuildingDetailAttribute_basementUsage char(10), uro_BuildingDetailAttribute_basementFirstUsage char(10), uro_BuildingDetailAttribute_basementSecondUsage char(10), uro_BuildingDetailAttribute_vacancy char(10), uro_BuildingDetailAttribute_buildingCoverageRate double, uro_BuildingDetailAttribute_floorAreaRate double, uro_BuildingDetailAttribute_specifiedBuildingCoverageRate double, uro_BuildingDetailAttribute_specifiedFloorAreaRate double, uro_BuildingDetailAttribute_standardFloorAreaRate double, uro_BuildingDetailAttribute_buildingHeight double, uro_BuildingDetailAttribute_eaveHeight double, uro_BuildingDetailAttribute_note char(50), uro_BuildingDetailAttribute_surveyYear char(10), uro_LargeCustomerFacilityAttribute_class char(10), uro_LargeCustomerFacilityAttribute_name char(50), uro_LargeCustomerFacilityAttribute_capacity integer, uro_LargeCustomerFacilityAttribute_owner char(50), uro_LargeCustomerFacilityAttribute_totalFloorArea double, uro_LargeCustomerFacilityAttribute_totalStoreFloorArea double, uro_LargeCustomerFacilityAttribute_inauguralDate char(10), uro_LargeCustomerFacilityAttribute_keyTenants char(50), uro_LargeCustomerFacilityAttribute_availability char(5), uro_LargeCustomerFacilityAttribute_urbanPlanType char(5), uro_LargeCustomerFacilityAttribute_areaClassificationType char(10), uro_LargeCustomerFacilityAttribute_districtsAndZonesType1 char(10), uro_LargeCustomerFacilityAttribute_districtsAndZonesType2 char(10), uro_LargeCustomerFacilityAttribute_districtsAndZonesType3 char(10),
      uro_LargeCustomerFacilityAttribute_districtsAndZonesType4 char(10), uro_LargeCustomerFacilityAttribute_districtsAndZonesType5 char(10), uro_LargeCustomerFacilityAttribute_districtsAndZonesType6 char(10), uro_LargeCustomerFacilityAttribute_districtsAndZonesType7 char(10), uro_LargeCustomerFacilityAttribute_districtsAndZonesType8 char(10), uro_LargeCustomerFacilityAttribute_districtsAndZonesType9 char(10), uro_LargeCustomerFacilityAttribute_districtsAndZonesType10 char(10), uro_LargeCustomerFacilityAttribute_landUseType char(10), uro_LargeCustomerFacilityAttribute_reference char(50), uro_LargeCustomerFacilityAttribute_note char(50), uro_LargeCustomerFacilityAttribute_surveyYear char(10), uro_BuildingRiverFloodingRiskAttribute_description char(10), uro_BuildingRiverFloodingRiskAttribute_rank char(10), uro_BuildingRiverFloodingRiskAttribute_rankOrg char(10), uro_BuildingRiverFloodingRiskAttribute_depth double, uro_BuildingRiverFloodingRiskAttribute_adminType char(10), uro_BuildingRiverFloodingRiskAttribute_scale char(10), uro_BuildingRiverFloodingRiskAttribute_duration double, uro_BuildingTsunamiRiskAttribute_description char(10), uro_BuildingTsunamiRiskAttribute_rank char(10), uro_BuildingTsunamiRiskAttribute_rankOrg char(10), uro_BuildingTsunamiRiskAttribute_depth double, uro_BuildingHighTideRiskAttribute_description char(10), uro_BuildingHighTideRiskAttribute_rank char(10), uro_BuildingHighTideRiskAttribute_rankOrg char(10), uro_BuildingHighTideRiskAttribute_depth double, uro_BuildingInlandFloodingRiskAttribute_description char(10), uro_BuildingInlandFloodingRiskAttribute_rank char(10), uro_BuildingInlandFloodingRiskAttribute_rankOrg char(10), uro_BuildingInlandFloodingRiskAttribute_depth double,
      uro_BuildingLandSlideRiskAttribute_description1 char(10), uro_BuildingLandSlideRiskAttribute_areaType1 char(10), uro_BuildingLandSlideRiskAttribute_description2 char(10), uro_BuildingLandSlideRiskAttribute_areaType2 char(10), uro_BuildingLandSlideRiskAttribute_description3 char(10), uro_BuildingLandSlideRiskAttribute_areaType3 char(10), uro_KeyValuePairAttribute_key1 char(10), uro_KeyValuePairAttribute_codeValue1 char(10), uro_KeyValuePairAttribute_key2 char(10), uro_KeyValuePairAttribute_codeValue2 char(10), uro_KeyValuePairAttribute_key3 char(10), uro_KeyValuePairAttribute_codeValue3 char(10), uro_KeyValuePairAttribute_key4 char(10), uro_KeyValuePairAttribute_codeValue4 char(10), uro_KeyValuePairAttribute_key5 char(10), uro_KeyValuePairAttribute_codeValue5 char(10), uro_KeyValuePairAttribute_key6 char(10), uro_KeyValuePairAttribute_codeValue6 char(10), uro_KeyValuePairAttribute_key7 char(10), uro_KeyValuePairAttribute_codeValue7 char(10), uro_KeyValuePairAttribute_key8 char(10), uro_KeyValuePairAttribute_codeValue8 char(10), uro_KeyValuePairAttribute_key9 char(10), uro_KeyValuePairAttribute_codeValue9 char(10), uro_KeyValuePairAttribute_key10 char(10), uro_KeyValuePairAttribute_codeValue10 char(10), uro_BuildingDataQualityAttribute_srcScale1 char(10), uro_BuildingDataQualityAttribute_srcScale2 char(10), uro_BuildingDataQualityAttribute_srcScale3 char(10), uro_BuildingDataQualityAttribute_srcScale4 char(10),
      uro_BuildingDataQualityAttribute_srcScale5 char(10), uro_BuildingDataQualityAttribute_srcScale6 char(10), uro_BuildingDataQualityAttribute_srcScale7 char(10), uro_BuildingDataQualityAttribute_srcScale8 char(10), uro_BuildingDataQualityAttribute_srcScale9 char(10), uro_BuildingDataQualityAttribute_srcScale10 char(10), uro_BuildingDataQualityAttribute_geometrySrcDesc1 char(10), uro_BuildingDataQualityAttribute_geometrySrcDesc2 char(10), uro_BuildingDataQualityAttribute_geometrySrcDesc3 char(10), uro_BuildingDataQualityAttribute_geometrySrcDesc4 char(10), uro_BuildingDataQualityAttribute_geometrySrcDesc5 char(10), uro_BuildingDataQualityAttribute_geometrySrcDesc6 char(10), uro_BuildingDataQualityAttribute_geometrySrcDesc7 char(10), uro_BuildingDataQualityAttribute_geometrySrcDesc8 char(10), uro_BuildingDataQualityAttribute_geometrySrcDesc9 char(10), uro_BuildingDataQualityAttribute_geometrySrcDesc10 char(10), uro_BuildingDataQualityAttribute_thematicSrcDesc1 char(10), uro_BuildingDataQualityAttribute_thematicSrcDesc2 char(10), uro_BuildingDataQualityAttribute_thematicSrcDesc3 char(10), uro_BuildingDataQualityAttribute_thematicSrcDesc4 char(10), uro_BuildingDataQualityAttribute_thematicSrcDesc5 char(10), uro_BuildingDataQualityAttribute_thematicSrcDesc6 char(10), uro_BuildingDataQualityAttribute_thematicSrcDesc7 char(10), uro_BuildingDataQualityAttribute_thematicSrcDesc8 char(10), uro_BuildingDataQualityAttribute_thematicSrcDesc9 char(10), uro_BuildingDataQualityAttribute_thematicSrcDesc10 char(10), uro_BuildingDataQualityAttribute_appearanceSrcDesc1 char(10), uro_BuildingDataQualityAttribute_appearanceSrcDesc2 char(10), uro_BuildingDataQualityAttribute_appearanceSrcDesc3 char(10), uro_BuildingDataQualityAttribute_appearanceSrcDesc4 char(10),
      uro_BuildingDataQualityAttribute_appearanceSrcDesc5 char(10), uro_BuildingDataQualityAttribute_appearanceSrcDesc6 char(10), uro_BuildingDataQualityAttribute_appearanceSrcDesc7 char(10), uro_BuildingDataQualityAttribute_appearanceSrcDesc8 char(10), uro_BuildingDataQualityAttribute_appearanceSrcDesc9 char(10), uro_BuildingDataQualityAttribute_appearanceSrcDesc10 char(10), uro_BuildingDataQualityAttribute_lod1HeightType char(10), uro_BuildingDataQualityAttribute_lodType1 char(10), uro_BuildingDataQualityAttribute_lodType2 char(10), uro_BuildingDataQualityAttribute_lodType3 char(10), xml_genericAttributeSet char(10000)
lod3_Building (writer GEODATABASE_FILE_1)
    attributes: bldg_Building_gml_id char(50), gml_description char(50), gml_name char(50), core_creationDate char(10), core_terminationDate char(10), bldg_class char(10), bldg_usage1 char(10), bldg_usage2 char(10), bldg_usage3 char(10), bldg_usage4 char(10), bldg_usage5 char(10), bldg_usage6 char(10), bldg_usage7 char(10), bldg_usage8 char(10), bldg_usage9 char(10), bldg_usage10 char(10), bldg_yearOfConstruction char(10), bldg_yearOfDemolition char(10), bldg_roofType char(10), bldg_measuredHeight double, bldg_storeysAboveGround integer, bldg_storeysBelowGround integer, bldg_storeyHeightsAboveGround double, bldg_storeyHeightsBelowGround double, bldg_address char(50), uro_buildingIDAttribute_buildingID char(50), uro_buildingIDAttribute_partID integer, uro_buildingIDAttribute_prefecture char(50), uro_buildingIDAttribute_city char(50), uro_BuildingDetailAttribute_serialNumberOfBuildingCertification char(50),
      uro_BuildingDetailAttribute_siteArea double, uro_BuildingDetailAttribute_totalFloorArea double, uro_BuildingDetailAttribute_buildingFootprintArea double, uro_BuildingDetailAttribute_buildingRoofEdgeArea double, uro_BuildingDetailAttribute_developmentArea double, uro_BuildingDetailAttribute_buildingStructureType char(10), uro_BuildingDetailAttribute_buildingStructureOrgType char(10), uro_BuildingDetailAttribute_fireproofStructureType char(10), uro_BuildingDetailAttribute_implementingBody char(50), uro_BuildingDetailAttribute_urbanPlanType char(10), uro_BuildingDetailAttribute_areaClassificationType char(10), uro_BuildingDetailAttribute_districtsAndZonesType1 char(10), uro_BuildingDetailAttribute_districtsAndZonesType2 char(10), uro_BuildingDetailAttribute_districtsAndZonesType3 char(10), uro_BuildingDetailAttribute_districtsAndZonesType4 char(10), uro_BuildingDetailAttribute_districtsAndZonesType5 char(10), uro_BuildingDetailAttribute_districtsAndZonesType6 char(10), uro_BuildingDetailAttribute_districtsAndZonesType7 char(10), uro_BuildingDetailAttribute_districtsAndZonesType8 char(10), uro_BuildingDetailAttribute_districtsAndZonesType9 char(10), uro_BuildingDetailAttribute_districtsAndZonesType10 char(10), uro_BuildingDetailAttribute_landUseType char(10), uro_BuildingDetailAttribute_reference char(10), uro_BuildingDetailAttribute_majorUsage char(10), uro_BuildingDetailAttribute_majorUsage2 char(10), uro_BuildingDetailAttribute_orgUsage char(10), uro_BuildingDetailAttribute_orgUsage2 char(10), uro_BuildingDetailAttribute_detailedUsage char(10), uro_BuildingDetailAttribute_detailedUsage2 char(10), uro_BuildingDetailAttribute_detailedUsage3 char(10),
      uro_BuildingDetailAttribute_groundFloorUsage char(10), uro_BuildingDetailAttribute_secondFloorUsage char(10), uro_BuildingDetailAttribute_thirdFloorUsage char(10), uro_BuildingDetailAttribute_basementUsage char(10), uro_BuildingDetailAttribute_basementFirstUsage char(10), uro_BuildingDetailAttribute_basementSecondUsage char(10), uro_BuildingDetailAttribute_vacancy char(10), uro_BuildingDetailAttribute_buildingCoverageRate double, uro_BuildingDetailAttribute_floorAreaRate double, uro_BuildingDetailAttribute_specifiedBuildingCoverageRate double, uro_BuildingDetailAttribute_specifiedFloorAreaRate double, uro_BuildingDetailAttribute_standardFloorAreaRate double, uro_BuildingDetailAttribute_buildingHeight double, uro_BuildingDetailAttribute_eaveHeight double, uro_BuildingDetailAttribute_note char(50), uro_BuildingDetailAttribute_surveyYear char(10), uro_LargeCustomerFacilityAttribute_class char(10), uro_LargeCustomerFacilityAttribute_name char(50), uro_LargeCustomerFacilityAttribute_capacity integer, uro_LargeCustomerFacilityAttribute_owner char(50), uro_LargeCustomerFacilityAttribute_totalFloorArea double, uro_LargeCustomerFacilityAttribute_totalStoreFloorArea double, uro_LargeCustomerFacilityAttribute_inauguralDate char(10), uro_LargeCustomerFacilityAttribute_keyTenants char(50), uro_LargeCustomerFacilityAttribute_availability char(5), uro_LargeCustomerFacilityAttribute_urbanPlanType char(5), uro_LargeCustomerFacilityAttribute_areaClassificationType char(10), uro_LargeCustomerFacilityAttribute_districtsAndZonesType1 char(10), uro_LargeCustomerFacilityAttribute_districtsAndZonesType2 char(10), uro_LargeCustomerFacilityAttribute_districtsAndZonesType3 char(10),
      uro_LargeCustomerFacilityAttribute_districtsAndZonesType4 char(10), uro_LargeCustomerFacilityAttribute_districtsAndZonesType5 char(10), uro_LargeCustomerFacilityAttribute_districtsAndZonesType6 char(10), uro_LargeCustomerFacilityAttribute_districtsAndZonesType7 char(10), uro_LargeCustomerFacilityAttribute_districtsAndZonesType8 char(10), uro_LargeCustomerFacilityAttribute_districtsAndZonesType9 char(10), uro_LargeCustomerFacilityAttribute_districtsAndZonesType10 char(10), uro_LargeCustomerFacilityAttribute_landUseType char(10), uro_LargeCustomerFacilityAttribute_reference char(50), uro_LargeCustomerFacilityAttribute_note char(50), uro_LargeCustomerFacilityAttribute_surveyYear char(10), uro_BuildingRiverFloodingRiskAttribute_description char(10), uro_BuildingRiverFloodingRiskAttribute_rank char(10), uro_BuildingRiverFloodingRiskAttribute_rankOrg char(10), uro_BuildingRiverFloodingRiskAttribute_depth double, uro_BuildingRiverFloodingRiskAttribute_adminType char(10), uro_BuildingRiverFloodingRiskAttribute_scale char(10), uro_BuildingRiverFloodingRiskAttribute_duration double, uro_BuildingTsunamiRiskAttribute_description char(10), uro_BuildingTsunamiRiskAttribute_rank char(10), uro_BuildingTsunamiRiskAttribute_rankOrg char(10), uro_BuildingTsunamiRiskAttribute_depth double, uro_BuildingHighTideRiskAttribute_description char(10), uro_BuildingHighTideRiskAttribute_rank char(10), uro_BuildingHighTideRiskAttribute_rankOrg char(10), uro_BuildingHighTideRiskAttribute_depth double, uro_BuildingInlandFloodingRiskAttribute_description char(10), uro_BuildingInlandFloodingRiskAttribute_rank char(10), uro_BuildingInlandFloodingRiskAttribute_rankOrg char(10), uro_BuildingInlandFloodingRiskAttribute_depth double,
      uro_BuildingLandSlideRiskAttribute_description1 char(10), uro_BuildingLandSlideRiskAttribute_areaType1 char(10), uro_BuildingLandSlideRiskAttribute_description2 char(10), uro_BuildingLandSlideRiskAttribute_areaType2 char(10), uro_BuildingLandSlideRiskAttribute_description3 char(10), uro_BuildingLandSlideRiskAttribute_areaType3 char(10), uro_KeyValuePairAttribute_key1 char(10), uro_KeyValuePairAttribute_codeValue1 char(10), uro_KeyValuePairAttribute_key2 char(10), uro_KeyValuePairAttribute_codeValue2 char(10), uro_KeyValuePairAttribute_key3 char(10), uro_KeyValuePairAttribute_codeValue3 char(10), uro_KeyValuePairAttribute_key4 char(10), uro_KeyValuePairAttribute_codeValue4 char(10), uro_KeyValuePairAttribute_key5 char(10), uro_KeyValuePairAttribute_codeValue5 char(10), uro_KeyValuePairAttribute_key6 char(10), uro_KeyValuePairAttribute_codeValue6 char(10), uro_KeyValuePairAttribute_key7 char(10), uro_KeyValuePairAttribute_codeValue7 char(10), uro_KeyValuePairAttribute_key8 char(10), uro_KeyValuePairAttribute_codeValue8 char(10), uro_KeyValuePairAttribute_key9 char(10), uro_KeyValuePairAttribute_codeValue9 char(10), uro_KeyValuePairAttribute_key10 char(10), uro_KeyValuePairAttribute_codeValue10 char(10), uro_BuildingDataQualityAttribute_srcScale1 char(10), uro_BuildingDataQualityAttribute_srcScale2 char(10), uro_BuildingDataQualityAttribute_srcScale3 char(10), uro_BuildingDataQualityAttribute_srcScale4 char(10),
      uro_BuildingDataQualityAttribute_srcScale5 char(10), uro_BuildingDataQualityAttribute_srcScale6 char(10), uro_BuildingDataQualityAttribute_srcScale7 char(10), uro_BuildingDataQualityAttribute_srcScale8 char(10), uro_BuildingDataQualityAttribute_srcScale9 char(10), uro_BuildingDataQualityAttribute_srcScale10 char(10), uro_BuildingDataQualityAttribute_geometrySrcDesc1 char(10), uro_BuildingDataQualityAttribute_geometrySrcDesc2 char(10), uro_BuildingDataQualityAttribute_geometrySrcDesc3 char(10), uro_BuildingDataQualityAttribute_geometrySrcDesc4 char(10), uro_BuildingDataQualityAttribute_geometrySrcDesc5 char(10), uro_BuildingDataQualityAttribute_geometrySrcDesc6 char(10), uro_BuildingDataQualityAttribute_geometrySrcDesc7 char(10), uro_BuildingDataQualityAttribute_geometrySrcDesc8 char(10), uro_BuildingDataQualityAttribute_geometrySrcDesc9 char(10), uro_BuildingDataQualityAttribute_geometrySrcDesc10 char(10), uro_BuildingDataQualityAttribute_thematicSrcDesc1 char(10), uro_BuildingDataQualityAttribute_thematicSrcDesc2 char(10), uro_BuildingDataQualityAttribute_thematicSrcDesc3 char(10), uro_BuildingDataQualityAttribute_thematicSrcDesc4 char(10), uro_BuildingDataQualityAttribute_thematicSrcDesc5 char(10), uro_BuildingDataQualityAttribute_thematicSrcDesc6 char(10), uro_BuildingDataQualityAttribute_thematicSrcDesc7 char(10), uro_BuildingDataQualityAttribute_thematicSrcDesc8 char(10), uro_BuildingDataQualityAttribute_thematicSrcDesc9 char(10), uro_BuildingDataQualityAttribute_thematicSrcDesc10 char(10), uro_BuildingDataQualityAttribute_appearanceSrcDesc1 char(10), uro_BuildingDataQualityAttribute_appearanceSrcDesc2 char(10), uro_BuildingDataQualityAttribute_appearanceSrcDesc3 char(10), uro_BuildingDataQualityAttribute_appearanceSrcDesc4 char(10),
      uro_BuildingDataQualityAttribute_appearanceSrcDesc5 char(10), uro_BuildingDataQualityAttribute_appearanceSrcDesc6 char(10), uro_BuildingDataQualityAttribute_appearanceSrcDesc7 char(10), uro_BuildingDataQualityAttribute_appearanceSrcDesc8 char(10), uro_BuildingDataQualityAttribute_appearanceSrcDesc9 char(10), uro_BuildingDataQualityAttribute_appearanceSrcDesc10 char(10), uro_BuildingDataQualityAttribute_lod1HeightType char(10), uro_BuildingDataQualityAttribute_lodType1 char(10), uro_BuildingDataQualityAttribute_lodType2 char(10), uro_BuildingDataQualityAttribute_lodType3 char(10), xml_genericAttributeSet char(10000)

Bookmark: Generic プロパティ
text_line (reader TEXTLINE_1)
    attributes: text_line_data buffer
    -> Sampler

Bookmark: インプット
lod0_Building (reader GEODATABASE_XML_1)
    attributes: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

FME custom transformer Domain_Attribute_Joiner

BuildingPart (output)
Building (output)
