FME workspace luse_plateau_v23_v200.fmw

Parameters:
- SourceDataset_CITYGML =   # Input CityGML File(s)
- TEMPLATEFILE_GEODATABASE_FILE =   # Template XML Workspace Document (Schema Only)
- DestDataset_GEODATABASE_FILE =   # Output File Geodatabase

Readers:
- TEXTLINE_1: TEXTLINE from $(SourceDataset_CITYGML)
- CITYGML_1: CITYGML from $(SourceDataset_CITYGML)
- GEODATABASE_XML_1: GEODATABASE_XML from $(TEMPLATEFILE_GEODATABASE_FILE)

Writers:
- GEODATABASE_FILE_1: GEODATABASE_FILE to $(DestDataset_GEODATABASE_FILE)

LandUse (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_level_of_detail{} xml_buffer, uro_land_use_detail_attribute{}.uro_land_use_detail_attribute_uro_org_land_use xml_buffer, uro_land_use_detail_attribute{}.uro_land_use_detail_attribute_uro_org_land_use_codeSpace xml_buffer, uro_land_use_detail_attribute{}.uro_land_use_detail_attribute_uro_nominal_area xml_real64, uro_land_use_detail_attribute{}.uro_land_use_detail_attribute_uro_nominal_area_units xml_buffer, uro_land_use_detail_attribute{}.uro_land_use_detail_attribute_uro_owner_type xml_buffer, uro_land_use_detail_attribute{}.uro_land_use_detail_attribute_uro_owner_type_codeSpace xml_buffer, uro_land_use_detail_attribute{}.uro_land_use_detail_attribute_uro_owner xml_buffer, uro_land_use_detail_attribute{}.uro_land_use_detail_attribute_uro_area_in_square_meter xml_real64, uro_land_use_detail_attribute{}.uro_land_use_detail_attribute_uro_area_in_square_meter_units xml_buffer,
      uro_land_use_detail_attribute{}.uro_land_use_detail_attribute_uro_area_in_ha xml_real64, uro_land_use_detail_attribute{}.uro_land_use_detail_attribute_uro_area_in_ha_units xml_buffer, uro_land_use_detail_attribute{}.uro_land_use_detail_attribute_uro_building_coverage_rate xml_real64, uro_land_use_detail_attribute{}.uro_land_use_detail_attribute_uro_floor_area_rate xml_real64, uro_land_use_detail_attribute{}.uro_land_use_detail_attribute_uro_specified_building_coverage_rate xml_real64, uro_land_use_detail_attribute{}.uro_land_use_detail_attribute_uro_specified_floor_area_rate xml_real64, uro_land_use_detail_attribute{}.uro_land_use_detail_attribute_uro_standard_floor_area_rate xml_real64, uro_land_use_detail_attribute{}.uro_land_use_detail_attribute_uro_urban_plan_type xml_buffer, uro_land_use_detail_attribute{}.uro_land_use_detail_attribute_uro_urban_plan_type_codeSpace xml_buffer, uro_land_use_detail_attribute{}.uro_land_use_detail_attribute_uro_area_classification_type xml_buffer, uro_land_use_detail_attribute{}.uro_land_use_detail_attribute_uro_area_classification_type_codeSpace xml_buffer, uro_land_use_detail_attribute{}.uro_land_use_detail_attribute_uro_districts_and_zones_type{} xml_buffer, uro_land_use_detail_attribute{}.uro_land_use_detail_attribute_uro_districts_and_zones_type{}.codeSpace xml_buffer, uro_land_use_detail_attribute{}.uro_land_use_detail_attribute_uro_prefecture xml_buffer, uro_land_use_detail_attribute{}.uro_land_use_detail_attribute_uro_prefecture_codeSpace xml_buffer, uro_land_use_detail_attribute{}.uro_land_use_detail_attribute_uro_city xml_buffer, uro_land_use_detail_attribute{}.uro_land_use_detail_attribute_uro_city_codeSpace xml_buffer, uro_land_use_detail_attribute{}.uro_land_use_detail_attribute_uro_reference xml_buffer, uro_land_use_detail_attribute{}.uro_land_use_detail_attribute_uro_note xml_buffer, uro_land_use_detail_attribute{}.uro_land_use_detail_attribute_uro_survey_year xml_buffer
    -> AttributeCreator
AttributeCreator
    ATTR_TABLE:
      SET_TO uro_nominalArea = @Value(uro_land_use_detail_attribute{0}.uro_land_use_detail_attribute_uro_nominal_area)
      SET_TO uro_ownerType = @Value(uro_land_use_detail_attribute{0}.uro_land_use_detail_attribute_uro_owner_type)
      SET_TO uro_owner = @Value(uro_land_use_detail_attribute{0}.uro_land_use_detail_attribute_uro_owner)
      SET_TO uro_areaInSquareMeter = @Value(uro_land_use_detail_attribute{0}.uro_land_use_detail_attribute_uro_area_in_square_meter)
      SET_TO uro_areaInHa = @Value(uro_land_use_detail_attribute{0}.uro_land_use_detail_attribute_uro_area_in_ha)
      SET_TO uro_urbanPlanType = @Value(uro_land_use_detail_attribute{0}.uro_land_use_detail_attribute_uro_urban_plan_type)
      SET_TO uro_districtsAndZonesType = @Value(uro_land_use_detail_attribute{0}.uro_land_use_detail_attribute_uro_districts_and_zones_type{0})
      SET_TO uro_areaClassificationType = @Value(uro_land_use_detail_attribute{0}.uro_land_use_detail_attribute_uro_area_classification_type)
      SET_TO uro_prefecture = @Value(uro_land_use_detail_attribute{0}.uro_land_use_detail_attribute_uro_prefecture)
      SET_TO uro_city = @Value(uro_land_use_detail_attribute{0}.uro_land_use_detail_attribute_uro_city)
      SET_TO uro_survey_year = @Value(uro_land_use_detail_attribute{0}.uro_land_use_detail_attribute_uro_survey_year)
      SET_TO uro_specified_floor_area_rate = @Value(uro_land_use_detail_attribute{0}.uro_land_use_detail_attribute_uro_specified_floor_area_rate)
      SET_TO luse_usage = @Value(citygml_usage{0})
      SET_TO uro_org_land_use = @Value(uro_land_use_detail_attribute{0}.uro_land_use_detail_attribute_uro_org_land_use)
      SET_TO uro_note = @Value(uro_land_use_detail_attribute{0}.uro_land_use_detail_attribute_uro_note)
      SET_TO uro_reference = @Value(uro_land_use_detail_attribute{0}.uro_land_use_detail_attribute_uro_reference)
      SET_TO uro_specified_building_coverage_rate = @Value(uro_land_use_detail_attribute{0}.uro_land_use_detail_attribute_uro_specified_building_coverage_rate)
      SET_TO uro_standard_floor_area_rate = @Value(uro_land_use_detail_attribute{0}.uro_land_use_detail_attribute_uro_standard_floor_area_rate)
      SET_TO uro_building_coverage_rate = @Value(uro_land_use_detail_attribute{0}.uro_land_use_detail_attribute_uro_building_coverage_rate)
      SET_TO uro_floor_area_rate = @Value(uro_land_use_detail_attribute{0}.uro_land_use_detail_attribute_uro_floor_area_rate)
      SET_TO uro_specified_floor_area_rate = @Value(uro_land_use_detail_attribute{0}.uro_land_use_detail_attribute_uro_specified_floor_area_rate)
    -> AttributeEncoder
AttributeEncoder
    ATTRCHOICE = All Attributes
    DEST_ENCODING = utf-8
    TREAT_AS_BYTES = Honor Encoding
    -> AttributeManager
AttributeManager
    ATTR_TABLE:
      RENAME_SET_VALUE gml_id > luse_LandUse_gml_id
      RENAME_SET_VALUE citygml_class > luse_class
      RENAME_SET_VALUE uro_nominalArea > uro_landUseDetailAttribute_nominalArea
      RENAME_SET_VALUE uro_ownerType > uro_landUseDetailAttribute_ownerType
      RENAME_SET_VALUE uro_owner > uro_landUseDetailAttribute_owner
      RENAME_SET_VALUE uro_areaInSquareMeter > uro_landUseDetailAttribute_areaInSquareMeter
      RENAME_SET_VALUE uro_areaInHa > uro_landUseDetailAttribute_areaInHa
      RENAME_SET_VALUE uro_urbanPlanType > uro_landUseDetailAttribute_urbanPlanType
      RENAME_SET_VALUE uro_districtsAndZonesType > uro_landUseDetailAttribute_districtsAndZonesType
      RENAME_SET_VALUE uro_areaClassificationType > uro_landUseDetailAttribute_areaClassificationType
      RENAME_SET_VALUE uro_prefecture > uro_landUseDetailAttribute_prefecture
      RENAME_SET_VALUE uro_city > uro_landUseDetailAttribute_city
      RENAME_SET_VALUE uro_surveyYear > uro_landUseDetailAttribute_surveyYear
      REMOVE gml_parent_id
      REMOVE citygml_target_uri
      REMOVE citygml_feature_role
      REMOVE citygml_feature_role_attr_name
      REMOVE citygml_feature_role_attr_val
      RENAME_SET_VALUE citygml_creationDate > core_creationDate
      RENAME_SET_VALUE citygml_terminationDate > core_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_class_codeSpace
      REMOVE citygml_function{}
      REMOVE citygml_function{}.codeSpace
      REMOVE citygml_usage{}
      REMOVE citygml_usage{}.codeSpace
      REMOVE citygml_level_of_detail{}
      REMOVE uro_area_classification_type{}
      REMOVE uro_area_classification_type{}.codeSpace
      REMOVE uro_area_in_ha{}
      REMOVE uro_area_in_ha{}.units
      REMOVE uro_area_in_square_meter{}
      REMOVE uro_area_in_square_meter{}.units
      REMOVE uro_city{}
      REMOVE uro_city{}.codeSpace
      REMOVE uro_districts_and_zones_type{}
      REMOVE uro_districts_and_zones_type{}.codeSpace
      REMOVE uro_land_use_plan_type{}
      REMOVE uro_land_use_plan_type{}.codeSpace
      REMOVE uro_nominal_area{}
      REMOVE uro_nominal_area{}.units
      REMOVE uro_note{}
      REMOVE uro_owner{}
      REMOVE uro_owner_type{}
      REMOVE uro_owner_type{}.codeSpace
      REMOVE uro_prefecture{}
      REMOVE uro_prefecture{}.codeSpace
      REMOVE uro_reference{}
      REMOVE uro_survey_year{}
      REMOVE uro_urban_plan_type{}
      REMOVE uro_urban_plan_type{}.codeSpace
      REMOVE FID
      REMOVE landuse_id
      REMOVE uro_land_use_detail_attribute{}.uro_land_use_detail_attribute_uro_org_land_use
      REMOVE uro_land_use_detail_attribute{}.uro_land_use_detail_attribute_uro_nominal_area
      REMOVE uro_land_use_detail_attribute{}.uro_land_use_detail_attribute_uro_area_in_ha
      REMOVE uro_land_use_detail_attribute{}.uro_land_use_detail_attribute_uro_specified_floor_area_rate
      REMOVE uro_land_use_detail_attribute{}.uro_land_use_detail_attribute_uro_area_classification_type_codeSpace
      REMOVE uro_land_use_detail_attribute{}.uro_land_use_detail_attribute_uro_survey_year
      RENAME_SET_VALUE uro_survey_year > uro_landUseDetailAttribute_surveyYear
      RENAME_SET_VALUE uro_specified_floor_area_rate > uro_landUseDetailAttribute_specifiedFloorAreaRate
      RENAME_SET_VALUE uro_org_land_use > uro_landUseDetailAttribute_orgLandUse
      RENAME_SET_VALUE uro_note > uro_landUseDetailAttribute_note
      RENAME_SET_VALUE uro_reference > uro_landUseDetailAttribute_reference
      RENAME_SET_VALUE uro_specified_building_coverage_rate > uro_landUseDetailAttribute_specifiedBuildingCoverageRate
      RENAME_SET_VALUE uro_standard_floor_area_rate > uro_landUseDetailAttribute_standardFloorAreaRate
      RENAME_SET_VALUE uro_building_coverage_rate > uro_landUseDetailAttribute_buildingCoverageRate
      RENAME_SET_VALUE uro_floor_area_rate > uro_landUseDetailAttribute_floorAreaRate
    -> FeatureJoiner [LEFT]
Sampler
    RATE = 1
    SAMPLE_MODE = No
    SAMPLE_TYPE_LONG = First N Features
    SAMPLED -> XMLTemplater [ROOT]
    SAMPLED -> XMLTemplater [SUB]
    NOT_SAMPLED -> XMLTemplater [SUB]
XMLTemplater
    OUTPUT_XML_HEADER = Yes
    RESULT_ATTRIBUTE = _result
    ROOT_QUERY_EXPR:
      <root>{
          fme:process-features("SUB")
      }</root>
    SUB_QUERY_EXPR:
      declare namespace gml="http://www.opengis.net/gml";
      declare namespace gen="http://www.opengis.net/citygml/generics/2.0";
      declare namespace luse="http://www.opengis.net/citygml/landuse/2.0";

      {
      let $doc := fme:get-xml-attribute("text_line_data")
      for $b in $doc//luse:LandUse
      return
      <LandUse gml_id="{data($b/@gml:id)}">{
          for $genStrAttr in $b/gen:stringAttribute
          where $b/gen:stringAttribute
              let $tempgenstrname := "gen_"||{data($genStrAttr/@name)}
              let $genstrname := fn:translate($tempgenstrname, "・（(- 「」、。－+＋）)", "____________")
              let $genstrtype := "TEXT"
              return
              <attr name="{$genstrname}" type="{$genstrtype}">{data($genStrAttr/gen:value)}</attr>
          }{
          for $genIntAttr in $b/gen:intAttribute
          where $b/gen:intAttribute
              let $tempgenintname := "gen_"||{data($genIntAttr/@name)}
              let $genintname := fn:translate($tempgenintname, "・（(- 「」、。－+＋）)", "____________")
              let $geninttype := "LONG"
              return
              <attr name="{$genintname}" type="{$geninttype}">{data($genIntAttr/gen:value)}</attr>
          }{
          for $genDoubleAttr in $b/gen:doubleAttribute
          where $b/gen:doubleAttribute
              let $tempgendoublename := "gen_"||{data($genDoubleAttr/@name)}
              let $gendoublename := fn:translate($tempgendoublename, "・（(- 「」、。－+＋）)", "____________")
              let $gendoubletype := "DOUBLE"
              return
              <attr name="{$gendoublename}" type="{$gendoubletype}">{data($genDoubleAttr/gen:value)}</attr>
          }{
          for $genDateAttr in $b/gen:dateAttribute
          where $b/gen:dateAttribute
              let $tempgendatename := "gen_"||{data($genDateAttr/@name)}
              let $gendatename := fn:translate($tempgendatename, "・（(- 「」、。－+＋）)", "____________")
              let $gendatetype := "TEXT"
              return
              <attr name="{$gendatename}" type="{$gendatetype}">{data($genDateAttr/gen:value)}</attr>
          }{
          for $genUriAttr in $b/gen:uriAttribute
          where $b/gen:uriAttribute
              let $tempgenuriname := "gen_"||{data($genUriAttr/@name)}
              let $genuriname := fn:translate($tempgenuriname, "・（(- 「」、。－+＋）)", "____________")
              let $genuritype := "TEXT"
              return
              <attr name="{$genuriname}" type="{$genuritype}">{data($genUriAttr/gen:value)}</attr>
          }{
          for $genMeasureAttr in $b/gen:measureAttribute
          where $b/gen:measureAttribute
              let $tempgenmeasurename := "gen_"||{data($genMeasureAttr/@name)}
              let $genmeasurename := fn:translate($tempgenmeasurename, "・（(- 「」、。－+＋）)", "____________")
              let $genmeasuretype := "DOUBLE"
              return
              <attr name="{$genmeasurename}" type="{$genmeasuretype}">{data($genMeasureAttr/gen:value)}</attr>
          }{
          for $attrSet in $b/gen:genericAttributeSet
          where $attrSet/gen:measureAttribute
              for $measureAttr in $attrSet/gen:measureAttribute
              let $mtempname := "gen_"||{data($attrSet/@name)}||"_"||{data($measureAttr/@name)}
              let $mname := fn:translate($mtempname, "・（(- 「」、。－+＋）)", "____________")
              let $mtype := "DOUBLE"
              return
              <attr name="{$mname}" type="{$mtype}">{data($measureAttr/gen:value)}</attr>
          }{
          for $attrSet in $b/gen:genericAttributeSet
          where $attrSet/gen:intAttribute
              for $intAttr in $attrSet/gen:intAttribute
              let $itempname := "gen_"||{data($attrSet/@name)}||"_"||{data($intAttr/@name)}
              let $iname := fn:translate($itempname, "・（(- 「」、。－+＋）)", "____________")
              let $itype := "LONG"
              return
              <attr name="{$iname}" type="{$itype}">{data($intAttr/gen:value)}</attr>
          }{
          for $attrSet in $b/gen:genericAttributeSet
          where $attrSet/gen:stringAttribute
              for $stringAttr in $attrSet/gen:stringAttribute
              let $stempname := "gen_"||{data($attrSet/@name)}||"_"||{data($stringAttr/@name)}
              let $sname := fn:translate($stempname, "・（(- 「」、。－+＋）)", "____________")
              let $stype := "TEXT"
              return
              <attr name="{$sname}" type="{$stype}">{data($stringAttr/gen:value)}</attr>
          }{
          for $attrSet in $b/gen:genericAttributeSet
          where $attrSet/gen:doubleAttribute
              for $doubleAttr in $attrSet/gen:doubleAttribute
              let $dtempname := "gen_"||{data($attrSet/@name)}||"_"||{data($doubleAttr/@name)}
              let $dname := fn:translate($dtempname, "・（(- 「」、。－+＋）)", "____________")
              let $dtype := "DOUBLE"
              return
              <attr name="{$dname}" type="{$dtype}">{data($doubleAttr/gen:value)}</attr>
          }{
          for $attrSet in $b/gen:genericAttributeSet
          where $attrSet/gen:dateAttribute
              for $dateAttr in $attrSet/gen:dateAttribute
              let $datetempname := "gen_"||{data($attrSet/@name)}||"_"||{data($dateAttr/@name)}
              let $datename := fn:translate($datetempname, "・（(- 「」、。－+＋）)", "____________")
              let $datetype := "TEXT"
              return
              <attr name="{$datename}" type="{$datetype}">{data($dateAttr/gen:value)}</attr>
          }{
          for $attrSet in $b/gen:genericAttributeSet
          where $attrSet/gen:uriAttribute
              for $uriAttr in $attrSet/gen:uriAttribute
              let $utempname := "gen_"||{data($attrSet/@name)}||"_"||{data($uriAttr/@name)}
              let $uname := fn:translate($utempname, "・（(- 「」、。－+＋）)", "____________")
              let $utype := "TEXT"
              return
              <attr name="{$uname}" type="{$utype}">{data($uriAttr/gen:value)}</attr>
          }</LandUse>
      }
    VISIBLE_QUERY_VALIDATE = Yes
    -> TextDecoder
TextDecoder
    DEST_ATTR = _decoded
    ENCODING_TYPE = XML
    STRING_TO_DECODE = @Value(_result)
    -> XMLFormatter
XMLFormatter
    COLLAPSE_EMPTY_ELEMENT = No
    FORMATTING_CHOICE = Pretty-Print XML
    INDENT_SIZE = 1
    LIST_NAME = _xml_error
    NAMESPACE_CLEANUP = No
    OUTPUT_ENCODING = utf-8
    REMOVE_ALL_COMMENT = No
    REMOVE_EMPTY_ELEMENT = No
    REMOVE_XML_HEADER = no
    REPLACE_TABS_WITH_SPACES = no
    SCHEMALOC_CLEANUP = No
    TEXT_INDENT = no
    WHITESPACE_HANDLING = Preserve all whitespace
    XML_ATTR_TEXT = _decoded
    XML_INPUT_TYPE = Attribute Specifying XML Text
    XML_OUTPUT_ATTR = _result
    XML_OUTPUT_TYPE = Attribute
    PASSED -> AttributeKeeper
AttributeKeeper
    CREATE_BULK_MODE_FEATURES = NO
    KEEP_ATTRS = _result
    -> XMLFragmenter
XMLFragmenter
    ATTRIBUTE_XML = _result
    EMBEDDED_EXPRESSIONS = root/LandUse
    FEATURE_TYPES_FORMAT_NAME = XML
    MERGE_ATTRS = No
    REJECT_FEATURES_WITH_NO_FRAGMENTS = YES
    XML_SOURCE_TYPE = Attribute with XML document
    FRAGMENTS -> XMLXQueryExtractor
XMLXQueryExtractor
    NEW_ATTRIBUTES = landuse_id
    QUERY_EXPR:
      declare namespace gml="http://www.opengis.net/gml";
      declare namespace gen="http://www.opengis.net/citygml/generics/2.0";
      declare namespace luse="http://www.opengis.net/citygml/landuse/2.0";

      fme:set-attribute('landuse_id', data(/LandUse/@gml_id))
    RESULT_ATTRIBUTE = _result
    RESULT_TYPE_NAME = Separated values
    SEPARATOR_VALUE = ,
    WRITE_XML_HEADER = No
    XML_ATTR = xml_fragment
    XML_REMOVE_SOURCE_ATTR = No
    XML_TYPE = Attribute specifying XML
    XQUERY_TYPE = XQuery expression
    QUERY_RESULTS -> AttributeManager_2
AttributeManager_2
    ATTR_TABLE:
      RENAME_SET_VALUE xml_fragment > xml_genericAttributeSet
      REMOVE xml_id
      REMOVE xml_matched_element
      REMOVE xml_parent_id
      REMOVE xml_parent_child_pos
      REMOVE _result
    USER_EXPOSED_ATTRIBUTES = building_id
    -> FeatureJoiner [RIGHT]
FeatureJoiner
    ATTR_CONFLICT_RES = Prefer Left
    GEOMETRY_HANDLING = Prefer Left
    JOIN_KEYS = luse_LandUse_gml_id landuse_id AUTO
    JOIN_MODE = Inner
    JOINED -> GeometryPartExtractor
GeometryPartExtractor
    GQUERY:
      for $geom in //geometry
      where $geom/parent::geometry/@fme_geometry_type = 'IFMEFace'
      return number($geom/@fme_id)
    EXTRACTED -> lod1_LandUse (writer GEODATABASE_FILE_1)
lod1_LandUse (writer GEODATABASE_FILE_1)
    attributes: luse_LandUse_gml_id char(50), gml_description char(50), gml_name char(50), core_creationDate char(10), core_terminationDate char(10), luse_class coded_domain(Common_landUseType:char(10):201:田（水田）:202:畑（畑、樹園地、採草地、養鶏（牛・豚）場）:203:山林（樹林地）:204:水面（河川水面、湖沼、ため池、用水路、濠、運河水面）:205:その他自然地（原野・牧野、荒れ地、低湿地、河川敷・河原、海浜、湖岸）:211:住宅用地（住宅、共同住宅、店舗等併用住宅、店舗等併用共同住宅、作業所併用住宅）:212:商業用地:213:工業用地:219:農林漁業施設用地:214:公益施設用地:215:道路用地（道路、駅前広場）:216:交通施設用地:217:公共空地（公園・緑地、広場、運動場、墓園）:218:その他公的施設用地（防衛施設用地）:220:その他の空地①（ゴルフ場）:221:その他空地②（太陽光発電のシステムを直接整備している土地）:222:その他の空地③（平面駐車場）:223:その他の空地④（その他の空地①～③以外の都市的土地利用：建物跡地、資材置場、改変工事中の土地、法面（道路、造成地等の主利用に含まれない法面））:231:不明:251:可住地:252:非可住地:260:農地（田、畑の区分がない）:261:宅地（住宅用地、商業用地等の区分が無い）:262:道路・鉄軌道敷（道路と交通施設用地が混在）:263:空地（その他の空地①～④の区分が無い）), luse_usage coded_domain(LandUse_usage:char(10):1:低未利用地:0:低未利用地以外), uro_landUseDetailAttribute_orgLandUse char(10), uro_landUseDetailAttribute_nominalArea double, uro_landUseDetailAttribute_ownerType coded_domain(LandUseDetailAttribute_ownerType:char(10):1010:国:1020:都道府県:1030:市区町村:1040:公社等:9000:未調査:9010:調査対象外:9020:不明), uro_landUseDetailAttribute_owner char(50), uro_landUseDetailAttribute_areaInSquareMeter double, uro_landUseDetailAttribute_areaInHa double, uro_landUseDetailAttribute_buildingCoverageRate double, uro_landUseDetailAttribute_floorAreaRate double, uro_landUseDetailAttribute_specifiedBuildingCoverageRate double, uro_landUseDetailAttribute_specifiedFloorAreaRate double, uro_landUseDetailAttribute_standardFloorAreaRate double, uro_landUseDetailAttribute_urbanPlanType char(10), uro_landUseDetailAttribute_areaClassificationType coded_domain(Common_areaClassificationType:char(10):22:市街化区域:23:市街化調整区域:24:非線引き用途地域:25:非線引き用途白地:31:居住誘導区域:32:都市機能誘導区域), uro_landUseDetailAttribute_districtsAndZonesType coded_domain(Common_districtsAndZonesType:char(10):0:用途地域の指定をしない区域:1:第1種低層住居専用地域:2:第2種低層住居専用地域:3:第1種中高層住居専用地域:4:第2種中高層住居専用地域:5:第1種住居地域:6:第2種住居地域:7:準住居地域:8:田園住居地域:9:近隣商業地域:10:商業地域:11:準工業地域:12:工業地域:13:工業専用地域:14:特別用途地区:15:特定用途制限地域:16:特例容積率適用地区:17:高層住居誘導地区:18:高度地区:19:高度利用地区:20:特定街区:21:都市再生特別地区:22:居住調整地域:23:特定用途誘導地区:24:防火地域:25:準防火地域:26:特定防災街区整備地区:27:景観地区:28:風致地区:29:駐車場整備地区:30:臨港地区:31:歴史的風土特別保存地区:32:第1種歴史的風土保存地区:33:第2種歴史的風土保存地区:34:緑地保全地域:35:特別緑地保存地区:36:緑化地域:37:流通業務地区:38:生産緑地地区:39:伝統的建造物群保存地区:40:航空機騒音障害防止地区:41:航空機騒音障害防止特別地区:42:居住環境向上用途誘導地区), uro_landUseDetailAttribute_prefecture coded_domain(Common_localPublicAuthorities_Prefecture:char(10):01:北海道:02:青森県:03:岩手県:04:宮城県:05:秋田県:06:山形県:07:福島県:08:茨城県:09:栃木県:10:群馬県:11:埼玉県:12:千葉県:13:東京都:14:神奈川県:15:新潟県:16:富山県:17:石川県:18:福井県:19:山梨県:20:長野県:21:岐阜県:22:静岡県:23:愛知県:24:三重県:25:滋賀県:26:京都府:27:大阪府:28:兵庫県:29:奈良県:30:和歌山県:31:鳥取県:32:島根県:33:岡山県:34:広島県:35:山口県:36:徳島県:37:香川県:38:愛媛県:39:高知県:40:福岡県:41:佐賀県:42:長崎県:43:熊本県:44:大分県:45:宮崎県:46:鹿児島県:47:沖縄県), uro_landUseDetailAttribute_city coded_domain(Common_localPublicAuthorities_City:char(10):01100:北海道札幌市:01101:北海道札幌市中央区:01102:北海道札幌市北区:01103:北海道札幌市東区:01104:北海道札幌市白石区:01105:北海道札幌市豊平区:01106:北海道札幌市南区:01107:北海道札幌市西区:01108:北海道札幌市厚別区:01109:北海道札幌市手稲区:01110:北海道札幌市清田区:01202:北海道函館市:01203:北海道小樽市:01204:北海道旭川市:01205:北海道室蘭市:01206:北海道釧路市:01207:北海道帯広市:01208:北海道北見市:01209:北海道夕張市:01210:北海道岩見沢市:01211:北海道網走市:01212:北海道留萌市:01213:北海道苫小牧市:01214:北海道稚内市:01215:北海道美唄市:01216:北海道芦別市:01217:北海道江別市:01218:北海道赤平市:01219:北海道紋別市:01220:北海道士別市:01221:北海道名寄市:01222:北海道三笠市:01223:北海道根室市:01224:北海道千歳市:01225:北海道滝川市:01226:北海道砂川市:01227:北海道歌志内市:01228:北海道深川市:01229:北海道富良野市:01230:北海道登別市:01231:北海道恵庭市:01233:北海道伊達市:01234:北海道北広島市:01235:北海道石狩市:01236:北海道北斗市:01303:北海道当別町:01304:北海道新篠津村:01331:北海道松前町:01332:北海道福島町:01333:北海道知内町:01334:北海道木古内町:01337:北海道七飯町:01343:北海道鹿部町:01345:北海道森町:01346:北海道八雲町:01347:北海道長万部町:01361:北海道江差町:01362:北海道上ノ国町:01363:北海道厚沢部町:01364:北海道乙部町:01367:北海道奥尻町:01370:北海道今金町:01371:北海道せたな町:01391:北海道島牧村:01392:北海道寿都町:01393:北海道黒松内町:01394:北海道蘭越町:01395:北海道ニセコ町:01396:北海道真狩村:01397:北海道留寿都村:01398:北海道喜茂別町:01399:北海道京極町:01400:北海道倶知安町:01401:北海道共和町:01402:北海道岩内町:01403:北海道泊村:01404:北海道神恵内村:01405:北海道積丹町:01406:北海道古平町:01407:北海道仁木町:01408:北海道余市町:01409:北海道赤井川村:01423:北海道南幌町:01424:北海道奈井江町:01425:北海道上砂川町:01427:北海道由仁町:01428:北海道長沼町:01429:北海道栗山町:01430:北海道月形町:01431:北海道浦臼町:01432:北海道新十津川町:01433:北海道妹背牛町:01434:北海道秩父別町:01436:北海道雨竜町:01437:北海道北竜町:01438:北海道沼田町:01452:北海道鷹栖町:01453:北海道東神楽町:01454:北海道当麻町:01455:北海道比布町:01456:北海道愛別町:01457:北海道上川町:01458:北海道東川町:01459:北海道美瑛町:01460:北海道上富良野町:01461:北海道中富良野町:01462:北海道南富良野町:01463:北海道占冠村:01464:北海道和寒町:01465:北海道剣淵町:01468:北海道下川町:01469:北海道美深町:01470:北海道音威子府村:01471:北海道中川町:01472:北海道幌加内町:01481:北海道増毛町:01482:北海道小平町:01483:北海道苫前町:01484:北海道羽幌町:01485:北海道初山別村:01486:北海道遠別町:01487:北海道天塩町:01511:北海道猿払村:01512:北海道浜頓別町:01513:北海道中頓別町:01514:北海道枝幸町:01516:北海道豊富町:01517:北海道礼文町:01518:北海道利尻町:01519:北海道利尻富士町:01520:北海道幌延町:01543:北海道美幌町:01544:北海道津別町:01545:北海道斜里町:01546:北海道清里町:01547:北海道小清水町:01549:北海道訓子府町:01550:北海道置戸町:01552:北海道佐呂間町:01555:北海道遠軽町:01559:北海道湧別町:01560:北海道滝上町:01561:北海道興部町:01562:北海道西興部村:01563:北海道雄武町:01564:北海道大空町:01571:北海道豊浦町:01575:北海道壮瞥町:01578:北海道白老町:01581:北海道厚真町:01584:北海道洞爺湖町:01585:北海道安平町:01586:北海道むかわ町:01601:北海道日高町:01602:北海道平取町:01604:北海道新冠町:01607:北海道浦河町:01608:北海道様似町:01609:北海道えりも町:01610:北海道新ひだか町:01631:北海道音更町:01632:北海道士幌町:01633:北海道上士幌町:01634:北海道鹿追町:01635:北海道新得町:01636:北海道清水町:01637:北海道芽室町:01638:北海道中札内村:01639:北海道更別村:01641:北海道大樹町:01642:北海道広尾町:01643:北海道幕別町:01644:北海道池田町:01645:北海道豊頃町:01646:北海道本別町:01647:北海道足寄町:01648:北海道陸別町:01649:北海道浦幌町:01661:北海道釧路町:01662:北海道厚岸町:01663:北海道浜中町:01664:北海道標茶町:01665:北海道弟子屈町:01667:北海道鶴居村:01668:北海道白糠町:01691:北海道別海町:01692:北海道中標津町:01693:北海道標津町:01694:北海道羅臼町:02201:青森県青森市:02202:青森県弘前市:02203:青森県八戸市:02204:青森県黒石市:02205:青森県五所川原市:02206:青森県十和田市:02207:青森県三沢市:02208:青森県むつ市:02209:青森県つがる市:02210:青森県平川市:02301:青森県平内町:02303:青森県今別町:02304:青森県蓬田村:02307:青森県外ヶ浜町:02321:青森県鰺ヶ沢町:02323:青森県深浦町:02343:青森県西目屋村:02361:青森県藤崎町:02362:青森県大鰐町:02367:青森県田舎館村:02381:青森県板柳町:02384:青森県鶴田町:02387:青森県中泊町:02401:青森県野辺地町:02402:青森県七戸町:02405:青森県六戸町:02406:青森県横浜町:02408:青森県東北町:02411:青森県六ヶ所村:02412:青森県おいらせ町:02423:青森県大間町:02424:青森県東通村:02425:青森県風間浦村:02426:青森県佐井村:02441:青森県三戸町:02442:青森県五戸町:02443:青森県田子町:02445:青森県南部町:02446:青森県階上町:02450:青森県新郷村:03201:岩手県盛岡市:03202:岩手県宮古市:03203:岩手県大船渡市:03205:岩手県花巻市:03206:岩手県北上市:03207:岩手県久慈市:03208:岩手県遠野市:03209:岩手県一関市:03210:岩手県陸前高田市:03211:岩手県釜石市:03213:岩手県二戸市:03214:岩手県八幡平市:03215:岩手県奥州市:03216:岩手県滝沢市:03301:岩手県雫石町:03302:岩手県葛巻町:03303:岩手県岩手町:03321:岩手県紫波町:03322:岩手県矢巾町:03366:岩手県西和賀町:03381:岩手県金ケ崎町:03402:岩手県平泉町:03441:岩手県住田町:03461:岩手県大槌町:03482:岩手県山田町:03483:岩手県岩泉町:03484:岩手県田野畑村:03485:岩手県普代村:03501:岩手県軽米町:03503:岩手県野田村:03506:岩手県九戸村:03507:岩手県洋野町:03524:岩手県一戸町:04100:宮城県仙台市:04101:宮城県仙台市青葉区:04102:宮城県仙台市宮城野区:04103:宮城県仙台市若林区:04104:宮城県仙台市太白区:04105:宮城県仙台市泉区:04202:宮城県石巻市:04203:宮城県塩竈市:04205:宮城県気仙沼市:04206:宮城県白石市:04207:宮城県名取市:04208:宮城県角田市:04209:宮城県多賀城市:04211:宮城県岩沼市:04212:宮城県登米市:04213:宮城県栗原市:04214:宮城県東松島市:04215:宮城県大崎市:04216:宮城県富谷市:04301:宮城県蔵王町:04302:宮城県七ヶ宿町:04321:宮城県大河原町:04322:宮城県村田町:04323:宮城県柴田町:04324:宮城県川崎町:04341:宮城県丸森町:04361:宮城県亘理町:04362:宮城県山元町:04401:宮城県松島町:04404:宮城県七ヶ浜町:04406:宮城県利府町:04421:宮城県大和町:04422:宮城県大郷町:04424:宮城県大衡村:04444:宮城県色麻町:04445:宮城県加美町:04501:宮城県涌谷町:04505:宮城県美里町:04581:宮城県女川町:04606:宮城県南三陸町:05201:秋田県秋田市:05202:秋田県能代市:05203:秋田県横手市:05204:秋田県大館市:05206:秋田県男鹿市:05207:秋田県湯沢市:05209:秋田県鹿角市:05210:秋田県由利本荘市:05211:秋田県潟上市:05212:秋田県大仙市:05213:秋田県北秋田市:05214:秋田県にかほ市:05215:秋田県仙北市:05303:秋田県小坂町:05327:秋田県上小阿仁村:05346:秋田県藤里町:05348:秋田県三種町:05349:秋田県八峰町:05361:秋田県五城目町:05363:秋田県八郎潟町:05366:秋田県井川町:05368:秋田県大潟村:05434:秋田県美郷町:05463:秋田県羽後町:05464:秋田県東成瀬村:06201:山形県山形市:06202:山形県米沢市:06203:山形県鶴岡市:06204:山形県酒田市:06205:山形県新庄市:06206:山形県寒河江市:06207:山形県上山市:06208:山形県村山市:06209:山形県長井市:06210:山形県天童市:06211:山形県東根市:06212:山形県尾花沢市:06213:山形県南陽市:06301:山形県山辺町:06302:山形県中山町:06321:山形県河北町:06322:山形県西川町:06323:山形県朝日町:06324:山形県大江町:06341:山形県大石田町:06361:山形県金山町:06362:山形県最上町:06363:山形県舟形町:06364:山形県真室川町:06365:山形県大蔵村:06366:山形県鮭川村:06367:山形県戸沢村:06381:山形県高畠町:06382:山形県川西町:06401:山形県小国町:06402:山形県白鷹町:06403:山形県飯豊町:06426:山形県三川町:06428:山形県庄内町:06461:山形県遊佐町:07201:福島県福島市:07202:福島県会津若松市:07203:福島県郡山市:07204:福島県いわき市:07205:福島県白河市:07207:福島県須賀川市:07208:福島県喜多方市:07209:福島県相馬市:07210:福島県二本松市:07211:福島県田村市:07212:福島県南相馬市:07213:福島県伊達市:07214:福島県本宮市:07301:福島県桑折町:07303:福島県国見町:07308:福島県川俣町:07322:福島県大玉村:07342:福島県鏡石町:07344:福島県天栄村:07362:福島県下郷町:07364:福島県檜枝岐村:07367:福島県只見町:07368:福島県南会津町:07402:福島県北塩原村:07405:福島県西会津町:07407:福島県磐梯町:07408:福島県猪苗代町:07421:福島県会津坂下町:07422:福島県湯川村:07423:福島県柳津町:07444:福島県三島町:07445:福島県金山町:07446:福島県昭和村:07447:福島県会津美里町:07461:福島県西郷村:07464:福島県泉崎村:07465:福島県中島村:07466:福島県矢吹町:07481:福島県棚倉町:07482:福島県矢祭町:07483:福島県塙町:07484:福島県鮫川村:07501:福島県石川町:07502:福島県玉川村:07503:福島県平田村:07504:福島県浅川町:07505:福島県古殿町:07521:福島県三春町:07522:福島県小野町:07541:福島県広野町:07542:福島県楢葉町:07543:福島県富岡町:07544:福島県川内村:07545:福島県大熊町:07546:福島県双葉町:07547:福島県浪江町:07548:福島県葛尾村:07561:福島県新地町:07564:福島県飯舘村:08201:茨城県水戸市:08202:茨城県日立市:08203:茨城県土浦市:08204:茨城県古河市:08205:茨城県石岡市:08207:茨城県結城市:08208:茨城県龍ケ崎市:08210:茨城県下妻市:08211:茨城県常総市:08212:茨城県常陸太田市:08214:茨城県高萩市:08215:茨城県北茨城市:08216:茨城県笠間市:08217:茨城県取手市:08219:茨城県牛久市:08220:茨城県つくば市:08221:茨城県ひたちなか市:08222:茨城県鹿嶋市:08223:茨城県潮来市:08224:茨城県守谷市:08225:茨城県常陸大宮市:08226:茨城県那珂市:08227:茨城県筑西市:08228:茨城県坂東市:08229:茨城県稲敷市:08230:茨城県かすみがうら市:08231:茨城県桜川市:08232:茨城県神栖市:08233:茨城県行方市:08234:茨城県鉾田市:08235:茨城県つくばみらい市:08236:茨城県小美玉市:08302:茨城県茨城町:08309:茨城県大洗町:08310:茨城県城里町:08341:茨城県東海村:08364:茨城県大子町:08442:茨城県美浦村:08443:茨城県阿見町:08447:茨城県河内町:08521:茨城県八千代町:08542:茨城県五霞町:08546:茨城県境町:08564:茨城県利根町:09201:栃木県宇都宮市:09202:栃木県足利市:09203:栃木県栃木市:09204:栃木県佐野市:09205:栃木県鹿沼市:09206:栃木県日光市:09208:栃木県小山市:09209:栃木県真岡市:09210:栃木県大田原市:09211:栃木県矢板市:09213:栃木県那須塩原市:09214:栃木県さくら市:09215:栃木県那須烏山市:09216:栃木県下野市:09301:栃木県上三川町:09342:栃木県益子町:09343:栃木県茂木町:09344:栃木県市貝町:09345:栃木県芳賀町:09361:栃木県壬生町:09364:栃木県野木町:09384:栃木県塩谷町:09386:栃木県高根沢町:09407:栃木県那須町:09411:栃木県那珂川町:10201:群馬県前橋市:10202:群馬県高崎市:10203:群馬県桐生市:10204:群馬県伊勢崎市:10205:群馬県太田市:10206:群馬県沼田市:10207:群馬県館林市:10208:群馬県渋川市:10209:群馬県藤岡市:10210:群馬県富岡市:10211:群馬県安中市:10212:群馬県みどり市:10344:群馬県榛東村:10345:群馬県吉岡町:10366:群馬県上野村:10367:群馬県神流町:10382:群馬県下仁田町:10383:群馬県南牧村:10384:群馬県甘楽町:10421:群馬県中之条町:10424:群馬県長野原町:10425:群馬県嬬恋村:10426:群馬県草津町:10428:群馬県高山村:10429:群馬県東吾妻町:10443:群馬県片品村:10444:群馬県川場村:10448:群馬県昭和村:10449:群馬県みなかみ町:10464:群馬県玉村町:10521:群馬県板倉町:10522:群馬県明和町:10523:群馬県千代田町:10524:群馬県大泉町:10525:群馬県邑楽町:11100:埼玉県さいたま市:11101:埼玉県さいたま市西区:11102:埼玉県さいたま市北区:11103:埼玉県さいたま市大宮区:11104:埼玉県さいたま市見沼区:11105:埼玉県さいたま市中央区:11106:埼玉県さいたま市桜区:11107:埼玉県さいたま市浦和区:11108:埼玉県さいたま市南区:11109:埼玉県さいたま市緑区:11110:埼玉県さいたま市岩槻区:11201:埼玉県川越市:11202:埼玉県熊谷市:11203:埼玉県川口市:11206:埼玉県行田市:11207:埼玉県秩父市:11208:埼玉県所沢市:11209:埼玉県飯能市:11210:埼玉県加須市:11211:埼玉県本庄市:11212:埼玉県東松山市:11214:埼玉県春日部市:11215:埼玉県狭山市:11216:埼玉県羽生市:11217:埼玉県鴻巣市:11218:埼玉県深谷市:11219:埼玉県上尾市:11221:埼玉県草加市:11222:埼玉県越谷市:11223:埼玉県蕨市:11224:埼玉県戸田市:11225:埼玉県入間市:11227:埼玉県朝霞市:11228:埼玉県志木市:11229:埼玉県和光市:11230:埼玉県新座市:11231:埼玉県桶川市:11232:埼玉県久喜市:11233:埼玉県北本市:11234:埼玉県八潮市:11235:埼玉県富士見市:11237:埼玉県三郷市:11238:埼玉県蓮田市:11239:埼玉県坂戸市:11240:埼玉県幸手市:11241:埼玉県鶴ヶ島市:11242:埼玉県日高市:11243:埼玉県吉川市:11245:埼玉県ふじみ野市:11246:埼玉県白岡市:11301:埼玉県伊奈町:11324:埼玉県三芳町:11326:埼玉県毛呂山町:11327:埼玉県越生町:11341:埼玉県滑川町:11342:埼玉県嵐山町:11343:埼玉県小川町:11346:埼玉県川島町:11347:埼玉県吉見町:11348:埼玉県鳩山町:11349:埼玉県ときがわ町:11361:埼玉県横瀬町:11362:埼玉県皆野町:11363:埼玉県長瀞町:11365:埼玉県小鹿野町:11369:埼玉県東秩父村:11381:埼玉県美里町:11383:埼玉県神川町:11385:埼玉県上里町:11408:埼玉県寄居町:11442:埼玉県宮代町:11464:埼玉県杉戸町:11465:埼玉県松伏町:12100:千葉県千葉市:12101:千葉県千葉市中央区:12102:千葉県千葉市花見川区:12103:千葉県千葉市稲毛区:12104:千葉県千葉市若葉区:12105:千葉県千葉市緑区:12106:千葉県千葉市美浜区:12202:千葉県銚子市:12203:千葉県市川市:12204:千葉県船橋市:12205:千葉県館山市:12206:千葉県木更津市:12207:千葉県松戸市:12208:千葉県野田市:12210:千葉県茂原市:12211:千葉県成田市:12212:千葉県佐倉市:12213:千葉県東金市:12215:千葉県旭市:12216:千葉県習志野市:12217:千葉県柏市:12218:千葉県勝浦市:12219:千葉県市原市:12220:千葉県流山市:12221:千葉県八千代市:12222:千葉県我孫子市:12223:千葉県鴨川市:12224:千葉県鎌ケ谷市:12225:千葉県君津市:12226:千葉県富津市:12227:千葉県浦安市:12228:千葉県四街道市:12229:千葉県袖ケ浦市:12230:千葉県八街市:12231:千葉県印西市:12232:千葉県白井市:12233:千葉県富里市:12234:千葉県南房総市:12235:千葉県匝瑳市:12236:千葉県香取市:12237:千葉県山武市:12238:千葉県いすみ市:12239:千葉県大網白里市:12322:千葉県酒々井町:12329:千葉県栄町:12342:千葉県神崎町:12347:千葉県多古町:12349:千葉県東庄町:12403:千葉県九十九里町:12409:千葉県芝山町:12410:千葉県横芝光町:12421:千葉県一宮町:12422:千葉県睦沢町:12423:千葉県長生村:12424:千葉県白子町:12426:千葉県長柄町:12427:千葉県長南町:12441:千葉県大多喜町:12443:千葉県御宿町:12463:千葉県鋸南町:13100:東京都特別区:13101:東京都千代田区:13102:東京都中央区:13103:東京都港区:13104:東京都新宿区:13105:東京都文京区:13106:東京都台東区:13107:東京都墨田区:13108:東京都江東区:13109:東京都品川区:13110:東京都目黒区:13111:東京都大田区:13112:東京都世田谷区:13113:東京都渋谷区:13114:東京都中野区:13115:東京都杉並区:13116:東京都豊島区:13117:東京都北区:13118:東京都荒川区:13119:東京都板橋区:13120:東京都練馬区:13121:東京都足立区:13122:東京都葛飾区:13123:東京都江戸川区:13201:東京都八王子市:13202:東京都立川市:13203:東京都武蔵野市:13204:東京都三鷹市:13205:東京都青梅市:13206:東京都府中市:13207:東京都昭島市:13208:東京都調布市:13209:東京都町田市:13210:東京都小金井市:13211:東京都小平市:13212:東京都日野市:13213:東京都東村山市:13214:東京都国分寺市:13215:東京都国立市:13218:東京都福生市:13219:東京都狛江市:13220:東京都東大和市:13221:東京都清瀬市:13222:東京都東久留米市:13223:東京都武蔵村山市:13224:東京都多摩市:13225:東京都稲城市:13227:東京都羽村市:13228:東京都あきる野市:13229:東京都西東京市:13303:東京都瑞穂町:13305:東京都日の出町:13307:東京都檜原村:13308:東京都奥多摩町:13361:東京都大島町:13362:東京都利島村:13363:東京都新島村:13364:東京都神津島村:13381:東京都三宅村:13382:東京都御蔵島村:13401:東京都八丈町:13402:東京都青ヶ島村:13421:東京都小笠原村:14100:神奈川県横浜市:14101:神奈川県横浜市鶴見区:14102:神奈川県横浜市神奈川区:14103:神奈川県横浜市西区:14104:神奈川県横浜市中区:14105:神奈川県横浜市南区:14106:神奈川県横浜市保土ケ谷区:14107:神奈川県横浜市磯子区:14108:神奈川県横浜市金沢区:14109:神奈川県横浜市港北区:14110:神奈川県横浜市戸塚区:14111:神奈川県横浜市港南区:14112:神奈川県横浜市旭区:14113:神奈川県横浜市緑区:14114:神奈川県横浜市瀬谷区:14115:神奈川県横浜市栄区:14116:神奈川県横浜市泉区:14117:神奈川県横浜市青葉区:14118:神奈川県横浜市都筑区:14130:神奈川県川崎市:14131:神奈川県川崎市川崎区:14132:神奈川県川崎市幸区:14133:神奈川県川崎市中原区:14134:神奈川県川崎市高津区:14135:神奈川県川崎市多摩区:14136:神奈川県川崎市宮前区:14137:神奈川県川崎市麻生区:14150:神奈川県相模原市:14151:神奈川県相模原市緑区:14152:神奈川県相模原市中央区:14153:神奈川県相模原市南区:14201:神奈川県横須賀市:14203:神奈川県平塚市:14204:神奈川県鎌倉市:14205:神奈川県藤沢市:14206:神奈川県小田原市:14207:神奈川県茅ヶ崎市:14208:神奈川県逗子市:14210:神奈川県三浦市:14211:神奈川県秦野市:14212:神奈川県厚木市:14213:神奈川県大和市:14214:神奈川県伊勢原市:14215:神奈川県海老名市:14216:神奈川県座間市:14217:神奈川県南足柄市:14218:神奈川県綾瀬市:14301:神奈川県葉山町:14321:神奈川県寒川町:14341:神奈川県大磯町:14342:神奈川県二宮町:14361:神奈川県中井町:14362:神奈川県大井町:14363:神奈川県松田町:14364:神奈川県山北町:14366:神奈川県開成町:14382:神奈川県箱根町:14383:神奈川県真鶴町:14384:神奈川県湯河原町:14401:神奈川県愛川町:14402:神奈川県清川村:15100:新潟県新潟市:15101:新潟県新潟市北区:15102:新潟県新潟市東区:15103:新潟県新潟市中央区:15104:新潟県新潟市江南区:15105:新潟県新潟市秋葉区:15106:新潟県新潟市南区:15107:新潟県新潟市西区:15108:新潟県新潟市西蒲区:15202:新潟県長岡市:15204:新潟県三条市:15205:新潟県柏崎市:15206:新潟県新発田市:15208:新潟県小千谷市:15209:新潟県加茂市:15210:新潟県十日町市:15211:新潟県見附市:15212:新潟県村上市:15213:新潟県燕市:15216:新潟県糸魚川市:15217:新潟県妙高市:15218:新潟県五泉市:15222:新潟県上越市:15223:新潟県阿賀野市:15224:新潟県佐渡市:15225:新潟県魚沼市:15226:新潟県南魚沼市:15227:新潟県胎内市:15307:新潟県聖籠町:15342:新潟県弥彦村:15361:新潟県田上町:15385:新潟県阿賀町:15405:新潟県出雲崎町:15461:新潟県湯沢町:15482:新潟県津南町:15504:新潟県刈羽村:15581:新潟県関川村:15586:新潟県粟島浦村:16201:富山県富山市:16202:富山県高岡市:16204:富山県魚津市:16205:富山県氷見市:16206:富山県滑川市:16207:富山県黒部市:16208:富山県砺波市:16209:富山県小矢部市:16210:富山県南砺市:16211:富山県射水市:16321:富山県舟橋村:16322:富山県上市町:16323:富山県立山町:16342:富山県入善町:16343:富山県朝日町:17201:石川県金沢市:17202:石川県七尾市:17203:石川県小松市:17204:石川県輪島市:17205:石川県珠洲市:17206:石川県加賀市:17207:石川県羽咋市:17209:石川県かほく市:17210:石川県白山市:17211:石川県能美市:17212:石川県野々市市:17324:石川県川北町:17361:石川県津幡町:17365:石川県内灘町:17384:石川県志賀町:17386:石川県宝達志水町:17407:石川県中能登町:17461:石川県穴水町:17463:石川県能登町:18201:福井県福井市:18202:福井県敦賀市:18204:福井県小浜市:18205:福井県大野市:18206:福井県勝山市:18207:福井県鯖江市:18208:福井県あわら市:18209:福井県越前市:18210:福井県坂井市:18322:福井県永平寺町:18382:福井県池田町:18404:福井県南越前町:18423:福井県越前町:18442:福井県美浜町:18481:福井県高浜町:18483:福井県おおい町:18501:福井県若狭町:19201:山梨県甲府市:19202:山梨県富士吉田市:19204:山梨県都留市:19205:山梨県山梨市:19206:山梨県大月市:19207:山梨県韮崎市:19208:山梨県南アルプス市:19209:山梨県北杜市:19210:山梨県甲斐市:19211:山梨県笛吹市:19212:山梨県上野原市:19213:山梨県甲州市:19214:山梨県中央市:19346:山梨県市川三郷町:19364:山梨県早川町:19365:山梨県身延町:19366:山梨県南部町:19368:山梨県富士川町:19384:山梨県昭和町:19422:山梨県道志村:19423:山梨県西桂町:19424:山梨県忍野村:19425:山梨県山中湖村:19429:山梨県鳴沢村:19430:山梨県富士河口湖町:19442:山梨県小菅村:19443:山梨県丹波山村:20201:長野県長野市:20202:長野県松本市:20203:長野県上田市:20204:長野県岡谷市:20205:長野県飯田市:20206:長野県諏訪市:20207:長野県須坂市:20208:長野県小諸市:20209:長野県伊那市:20210:長野県駒ヶ根市:20211:長野県中野市:20212:長野県大町市:20213:長野県飯山市:20214:長野県茅野市:20215:長野県塩尻市:20217:長野県佐久市:20218:長野県千曲市:20219:長野県東御市:20220:長野県安曇野市:20303:長野県小海町:20304:長野県川上村:20305:長野県南牧村:20306:長野県南相木村:20307:長野県北相木村:20309:長野県佐久穂町:20321:長野県軽井沢町:20323:長野県御代田町:20324:長野県立科町:20349:長野県青木村:20350:長野県長和町:20361:長野県下諏訪町:20362:長野県富士見町:20363:長野県原村:20382:長野県辰野町:20383:長野県箕輪町:20384:長野県飯島町:20385:長野県南箕輪村:20386:長野県中川村:20388:長野県宮田村:20402:長野県松川町:20403:長野県高森町:20404:長野県阿南町:20407:長野県阿智村:20409:長野県平谷村:20410:長野県根羽村:20411:長野県下條村:20412:長野県売木村:20413:長野県天龍村:20414:長野県泰阜村:20415:長野県喬木村:20416:長野県豊丘村:20417:長野県大鹿村:20422:長野県上松町:20423:長野県南木曽町:20425:長野県木祖村:20429:長野県王滝村:20430:長野県大桑村:20432:長野県木曽町:20446:長野県麻績村:20448:長野県生坂村:20450:長野県山形村:20451:長野県朝日村:20452:長野県筑北村:20481:長野県池田町:20482:長野県松川村:20485:長野県白馬村:20486:長野県小谷村:20521:長野県坂城町:20541:長野県小布施町:20543:長野県高山村:20561:長野県山ノ内町:20562:長野県木島平村:20563:長野県野沢温泉村:20583:長野県信濃町:20588:長野県小川村:20590:長野県飯綱町:20602:長野県栄村:21201:岐阜県岐阜市:21202:岐阜県大垣市:21203:岐阜県高山市:21204:岐阜県多治見市:21205:岐阜県関市:21206:岐阜県中津川市:21207:岐阜県美濃市:21208:岐阜県瑞浪市:21209:岐阜県羽島市:21210:岐阜県恵那市:21211:岐阜県美濃加茂市:21212:岐阜県土岐市:21213:岐阜県各務原市:21214:岐阜県可児市:21215:岐阜県山県市:21216:岐阜県瑞穂市:21217:岐阜県飛騨市:21218:岐阜県本巣市:21219:岐阜県郡上市:21220:岐阜県下呂市:21221:岐阜県海津市:21302:岐阜県岐南町:21303:岐阜県笠松町:21341:岐阜県養老町:21361:岐阜県垂井町:21362:岐阜県関ケ原町:21381:岐阜県神戸町:21382:岐阜県輪之内町:21383:岐阜県安八町:21401:岐阜県揖斐川町:21403:岐阜県大野町:21404:岐阜県池田町:21421:岐阜県北方町:21501:岐阜県坂祝町:21502:岐阜県富加町:21503:岐阜県川辺町:21504:岐阜県七宗町:21505:岐阜県八百津町:21506:岐阜県白川町:21507:岐阜県東白川村:21521:岐阜県御嵩町:21604:岐阜県白川村:22100:静岡県静岡市:22101:静岡県静岡市葵区:22102:静岡県静岡市駿河区:22103:静岡県静岡市清水区:22130:静岡県浜松市:22131:静岡県浜松市中区:22132:静岡県浜松市東区:22133:静岡県浜松市西区:22134:静岡県浜松市南区:22135:静岡県浜松市北区:22136:静岡県浜松市浜北区:22137:静岡県浜松市天竜区:22203:静岡県沼津市:22205:静岡県熱海市:22206:静岡県三島市:22207:静岡県富士宮市:22208:静岡県伊東市:22209:静岡県島田市:22210:静岡県富士市:22211:静岡県磐田市:22212:静岡県焼津市:22213:静岡県掛川市:22214:静岡県藤枝市:22215:静岡県御殿場市:22216:静岡県袋井市:22219:静岡県下田市:22220:静岡県裾野市:22221:静岡県湖西市:22222:静岡県伊豆市:22223:静岡県御前崎市:22224:静岡県菊川市:22225:静岡県伊豆の国市:22226:静岡県牧之原市:22301:静岡県東伊豆町:22302:静岡県河津町:22304:静岡県南伊豆町:22305:静岡県松崎町:22306:静岡県西伊豆町:22325:静岡県函南町:22341:静岡県清水町:22342:静岡県長泉町:22344:静岡県小山町:22424:静岡県吉田町:22429:静岡県川根本町:22461:静岡県森町:23100:愛知県名古屋市:23101:愛知県名古屋市千種区:23102:愛知県名古屋市東区:23103:愛知県名古屋市北区:23104:愛知県名古屋市西区:23105:愛知県名古屋市中村区:23106:愛知県名古屋市中区:23107:愛知県名古屋市昭和区:23108:愛知県名古屋市瑞穂区:23109:愛知県名古屋市熱田区:23110:愛知県名古屋市中川区:23111:愛知県名古屋市港区:23112:愛知県名古屋市南区:23113:愛知県名古屋市守山区:23114:愛知県名古屋市緑区:23115:愛知県名古屋市名東区:23116:愛知県名古屋市天白区:23201:愛知県豊橋市:23202:愛知県岡崎市:23203:愛知県一宮市:23204:愛知県瀬戸市:23205:愛知県半田市:23206:愛知県春日井市:23207:愛知県豊川市:23208:愛知県津島市:23209:愛知県碧南市:23210:愛知県刈谷市:23211:愛知県豊田市:23212:愛知県安城市:23213:愛知県西尾市:23214:愛知県蒲郡市:23215:愛知県犬山市:23216:愛知県常滑市:23217:愛知県江南市:23219:愛知県小牧市:23220:愛知県稲沢市:23221:愛知県新城市:23222:愛知県東海市:23223:愛知県大府市:23224:愛知県知多市:23225:愛知県知立市:23226:愛知県尾張旭市:23227:愛知県高浜市:23228:愛知県岩倉市:23229:愛知県豊明市:23230:愛知県日進市:23231:愛知県田原市:23232:愛知県愛西市:23233:愛知県清須市:23234:愛知県北名古屋市:23235:愛知県弥富市:23236:愛知県みよし市:23237:愛知県あま市:23238:愛知県長久手市:23302:愛知県東郷町:23342:愛知県豊山町:23361:愛知県大口町:23362:愛知県扶桑町:23424:愛知県大治町:23425:愛知県蟹江町:23427:愛知県飛島村:23441:愛知県阿久比町:23442:愛知県東浦町:23445:愛知県南知多町:23446:愛知県美浜町:23447:愛知県武豊町:23501:愛知県幸田町:23561:愛知県設楽町:23562:愛知県東栄町:23563:愛知県豊根村:24201:三重県津市:24202:三重県四日市市:24203:三重県伊勢市:24204:三重県松阪市:24205:三重県桑名市:24207:三重県鈴鹿市:24208:三重県名張市:24209:三重県尾鷲市:24210:三重県亀山市:24211:三重県鳥羽市:24212:三重県熊野市:24214:三重県いなべ市:24215:三重県志摩市:24216:三重県伊賀市:24303:三重県木曽岬町:24324:三重県東員町:24341:三重県菰野町:24343:三重県朝日町:24344:三重県川越町:24441:三重県多気町:24442:三重県明和町:24443:三重県大台町:24461:三重県玉城町:24470:三重県度会町:24471:三重県大紀町:24472:三重県南伊勢町:24543:三重県紀北町:24561:三重県御浜町:24562:三重県紀宝町:25201:滋賀県大津市:25202:滋賀県彦根市:25203:滋賀県長浜市:25204:滋賀県近江八幡市:25206:滋賀県草津市:25207:滋賀県守山市:25208:滋賀県栗東市:25209:滋賀県甲賀市:25210:滋賀県野洲市:25211:滋賀県湖南市:25212:滋賀県高島市:25213:滋賀県東近江市:25214:滋賀県米原市:25383:滋賀県日野町:25384:滋賀県竜王町:25425:滋賀県愛荘町:25441:滋賀県豊郷町:25442:滋賀県甲良町:25443:滋賀県多賀町:26100:京都府京都市:26101:京都府京都市北区:26102:京都府京都市上京区:26103:京都府京都市左京区:26104:京都府京都市中京区:26105:京都府京都市東山区:26106:京都府京都市下京区:26107:京都府京都市南区:26108:京都府京都市右京区:26109:京都府京都市伏見区:26110:京都府京都市山科区:26111:京都府京都市西京区:26201:京都府福知山市:26202:京都府舞鶴市:26203:京都府綾部市:26204:京都府宇治市:26205:京都府宮津市:26206:京都府亀岡市:26207:京都府城陽市:26208:京都府向日市:26209:京都府長岡京市:26210:京都府八幡市:26211:京都府京田辺市:26212:京都府京丹後市:26213:京都府南丹市:26214:京都府木津川市:26303:京都府大山崎町:26322:京都府久御山町:26343:京都府井手町:26344:京都府宇治田原町:26364:京都府笠置町:26365:京都府和束町:26366:京都府精華町:26367:京都府南山城村:26407:京都府京丹波町:26463:京都府伊根町:26465:京都府与謝野町:27100:大阪府大阪市:27102:大阪府大阪市都島区:27103:大阪府大阪市福島区:27104:大阪府大阪市此花区:27106:大阪府大阪市西区:27107:大阪府大阪市港区:27108:大阪府大阪市大正区:27109:大阪府大阪市天王寺区:27111:大阪府大阪市浪速区:27113:大阪府大阪市西淀川区:27114:大阪府大阪市東淀川区:27115:大阪府大阪市東成区:27116:大阪府大阪市生野区:27117:大阪府大阪市旭区:27118:大阪府大阪市城東区:27119:大阪府大阪市阿倍野区:27120:大阪府大阪市住吉区:27121:大阪府大阪市東住吉区:27122:大阪府大阪市西成区:27123:大阪府大阪市淀川区:27124:大阪府大阪市鶴見区:27125:大阪府大阪市住之江区:27126:大阪府大阪市平野区:27127:大阪府大阪市北区:27128:大阪府大阪市中央区:27140:大阪府堺市:27141:大阪府堺市堺区:27142:大阪府堺市中区:27143:大阪府堺市東区:27144:大阪府堺市西区:27145:大阪府堺市南区:27146:大阪府堺市北区:27147:大阪府堺市美原区:27202:大阪府岸和田市:27203:大阪府豊中市:27204:大阪府池田市:27205:大阪府吹田市:27206:大阪府泉大津市:27207:大阪府高槻市:27208:大阪府貝塚市:27209:大阪府守口市:27210:大阪府枚方市:27211:大阪府茨木市:27212:大阪府八尾市:27213:大阪府泉佐野市:27214:大阪府富田林市:27215:大阪府寝屋川市:27216:大阪府河内長野市:27217:大阪府松原市:27218:大阪府大東市:27219:大阪府和泉市:27220:大阪府箕面市:27221:大阪府柏原市:27222:大阪府羽曳野市:27223:大阪府門真市:27224:大阪府摂津市:27225:大阪府高石市:27226:大阪府藤井寺市:27227:大阪府東大阪市:27228:大阪府泉南市:27229:大阪府四條畷市:27230:大阪府交野市:27231:大阪府大阪狭山市:27232:大阪府阪南市:27301:大阪府島本町:27321:大阪府豊能町:27322:大阪府能勢町:27341:大阪府忠岡町:27361:大阪府熊取町:27362:大阪府田尻町:27366:大阪府岬町:27381:大阪府太子町:27382:大阪府河南町:27383:大阪府千早赤阪村:28100:兵庫県神戸市:28101:兵庫県神戸市東灘区:28102:兵庫県神戸市灘区:28105:兵庫県神戸市兵庫区:28106:兵庫県神戸市長田区:28107:兵庫県神戸市須磨区:28108:兵庫県神戸市垂水区:28109:兵庫県神戸市北区:28110:兵庫県神戸市中央区:28111:兵庫県神戸市西区:28201:兵庫県姫路市:28202:兵庫県尼崎市:28203:兵庫県明石市:28204:兵庫県西宮市:28205:兵庫県洲本市:28206:兵庫県芦屋市:28207:兵庫県伊丹市:28208:兵庫県相生市:28209:兵庫県豊岡市:28210:兵庫県加古川市:28212:兵庫県赤穂市:28213:兵庫県西脇市:28214:兵庫県宝塚市:28215:兵庫県三木市:28216:兵庫県高砂市:28217:兵庫県川西市:28218:兵庫県小野市:28219:兵庫県三田市:28220:兵庫県加西市:28221:兵庫県丹波篠山市:28222:兵庫県養父市:28223:兵庫県丹波市:28224:兵庫県南あわじ市:28225:兵庫県朝来市:28226:兵庫県淡路市:28227:兵庫県宍粟市:28228:兵庫県加東市:28229:兵庫県たつの市:28301:兵庫県猪名川町:28365:兵庫県多可町:28381:兵庫県稲美町:28382:兵庫県播磨町:28442:兵庫県市川町:28443:兵庫県福崎町:28446:兵庫県神河町:28464:兵庫県太子町:28481:兵庫県上郡町:28501:兵庫県佐用町:28585:兵庫県香美町:28586:兵庫県新温泉町:29201:奈良県奈良市:29202:奈良県大和高田市:29203:奈良県大和郡山市:29204:奈良県天理市:29205:奈良県橿原市:29206:奈良県桜井市:29207:奈良県五條市:29208:奈良県御所市:29209:奈良県生駒市:29210:奈良県香芝市:29211:奈良県葛城市:29212:奈良県宇陀市:29322:奈良県山添村:29342:奈良県平群町:29343:奈良県三郷町:29344:奈良県斑鳩町:29345:奈良県安堵町:29361:奈良県川西町:29362:奈良県三宅町:29363:奈良県田原本町:29385:奈良県曽爾村:29386:奈良県御杖村:29401:奈良県高取町:29402:奈良県明日香村:29424:奈良県上牧町:29425:奈良県王寺町:29426:奈良県広陵町:29427:奈良県河合町:29441:奈良県吉野町:29442:奈良県大淀町:29443:奈良県下市町:29444:奈良県黒滝村:29446:奈良県天川村:29447:奈良県野迫川村:29449:奈良県十津川村:29450:奈良県下北山村:29451:奈良県上北山村:29452:奈良県川上村:29453:奈良県東吉野村:30201:和歌山県和歌山市:30202:和歌山県海南市:30203:和歌山県橋本市:30204:和歌山県有田市:30205:和歌山県御坊市:30206:和歌山県田辺市:30207:和歌山県新宮市:30208:和歌山県紀の川市:30209:和歌山県岩出市:30304:和歌山県紀美野町:30341:和歌山県かつらぎ町:30343:和歌山県九度山町:30344:和歌山県高野町:30361:和歌山県湯浅町:30362:和歌山県広川町:30366:和歌山県有田川町:30381:和歌山県美浜町:30382:和歌山県日高町:30383:和歌山県由良町:30390:和歌山県印南町:30391:和歌山県みなべ町:30392:和歌山県日高川町:30401:和歌山県白浜町:30404:和歌山県上富田町:30406:和歌山県すさみ町:30421:和歌山県那智勝浦町:30422:和歌山県太地町:30424:和歌山県古座川町:30427:和歌山県北山村:30428:和歌山県串本町:31201:鳥取県鳥取市:31202:鳥取県米子市:31203:鳥取県倉吉市:31204:鳥取県境港市:31302:鳥取県岩美町:31325:鳥取県若桜町:31328:鳥取県智頭町:31329:鳥取県八頭町:31364:鳥取県三朝町:31370:鳥取県湯梨浜町:31371:鳥取県琴浦町:31372:鳥取県北栄町:31384:鳥取県日吉津村:31386:鳥取県大山町:31389:鳥取県南部町:31390:鳥取県伯耆町:31401:鳥取県日南町:31402:鳥取県日野町:31403:鳥取県江府町:32201:島根県松江市:32202:島根県浜田市:32203:島根県出雲市:32204:島根県益田市:32205:島根県大田市:32206:島根県安来市:32207:島根県江津市:32209:島根県雲南市:32343:島根県奥出雲町:32386:島根県飯南町:32441:島根県川本町:32448:島根県美郷町:32449:島根県邑南町:32501:島根県津和野町:32505:島根県吉賀町:32525:島根県海士町:32526:島根県西ノ島町:32527:島根県知夫村:32528:島根県隠岐の島町:33100:岡山県岡山市:33101:岡山県岡山市北区:33102:岡山県岡山市中区:33103:岡山県岡山市東区:33104:岡山県岡山市南区:33202:岡山県倉敷市:33203:岡山県津山市:33204:岡山県玉野市:33205:岡山県笠岡市:33207:岡山県井原市:33208:岡山県総社市:33209:岡山県高梁市:33210:岡山県新見市:33211:岡山県備前市:33212:岡山県瀬戸内市:33213:岡山県赤磐市:33214:岡山県真庭市:33215:岡山県美作市:33216:岡山県浅口市:33346:岡山県和気町:33423:岡山県早島町:33445:岡山県里庄町:33461:岡山県矢掛町:33586:岡山県新庄村:33606:岡山県鏡野町:33622:岡山県勝央町:33623:岡山県奈義町:33643:岡山県西粟倉村:33663:岡山県久米南町:33666:岡山県美咲町:33681:岡山県吉備中央町:34100:広島県広島市:34101:広島県広島市中区:34102:広島県広島市東区:34103:広島県広島市南区:34104:広島県広島市西区:34105:広島県広島市安佐南区:34106:広島県広島市安佐北区:34107:広島県広島市安芸区:34108:広島県広島市佐伯区:34202:広島県呉市:34203:広島県竹原市:34204:広島県三原市:34205:広島県尾道市:34207:広島県福山市:34208:広島県府中市:34209:広島県三次市:34210:広島県庄原市:34211:広島県大竹市:34212:広島県東広島市:34213:広島県廿日市市:34214:広島県安芸高田市:34215:広島県江田島市:34302:広島県府中町:34304:広島県海田町:34307:広島県熊野町:34309:広島県坂町:34368:広島県安芸太田町:34369:広島県北広島町:34431:広島県大崎上島町:34462:広島県世羅町:34545:広島県神石高原町:35201:山口県下関市:35202:山口県宇部市:35203:山口県山口市:35204:山口県萩市:35206:山口県防府市:35207:山口県下松市:35208:山口県岩国市:35210:山口県光市:35211:山口県長門市:35212:山口県柳井市:35213:山口県美祢市:35215:山口県周南市:35216:山口県山陽小野田市:35305:山口県周防大島町:35321:山口県和木町:35341:山口県上関町:35343:山口県田布施町:35344:山口県平生町:35502:山口県阿武町:36201:徳島県徳島市:36202:徳島県鳴門市:36203:徳島県小松島市:36204:徳島県阿南市:36205:徳島県吉野川市:36206:徳島県阿波市:36207:徳島県美馬市:36208:徳島県三好市:36301:徳島県勝浦町:36302:徳島県上勝町:36321:徳島県佐那河内村:36341:徳島県石井町:36342:徳島県神山町:36368:徳島県那賀町:36383:徳島県牟岐町:36387:徳島県美波町:36388:徳島県海陽町:36401:徳島県松茂町:36402:徳島県北島町:36403:徳島県藍住町:36404:徳島県板野町:36405:徳島県上板町:36468:徳島県つるぎ町:36489:徳島県東みよし町:37201:香川県高松市:37202:香川県丸亀市:37203:香川県坂出市:37204:香川県善通寺市:37205:香川県観音寺市:37206:香川県さぬき市:37207:香川県東かがわ市:37208:香川県三豊市:37322:香川県土庄町:37324:香川県小豆島町:37341:香川県三木町:37364:香川県直島町:37386:香川県宇多津町:37387:香川県綾川町:37403:香川県琴平町:37404:香川県多度津町:37406:香川県まんのう町:38201:愛媛県松山市:38202:愛媛県今治市:38203:愛媛県宇和島市:38204:愛媛県八幡浜市:38205:愛媛県新居浜市:38206:愛媛県西条市:38207:愛媛県大洲市:38210:愛媛県伊予市:38213:愛媛県四国中央市:38214:愛媛県西予市:38215:愛媛県東温市:38356:愛媛県上島町:38386:愛媛県久万高原町:38401:愛媛県松前町:38402:愛媛県砥部町:38422:愛媛県内子町:38442:愛媛県伊方町:38484:愛媛県松野町:38488:愛媛県鬼北町:38506:愛媛県愛南町:39201:高知県高知市:39202:高知県室戸市:39203:高知県安芸市:39204:高知県南国市:39205:高知県土佐市:39206:高知県須崎市:39208:高知県宿毛市:39209:高知県土佐清水市:39210:高知県四万十市:39211:高知県香南市:39212:高知県香美市:39301:高知県東洋町:39302:高知県奈半利町:39303:高知県田野町:39304:高知県安田町:39305:高知県北川村:39306:高知県馬路村:39307:高知県芸西村:39341:高知県本山町:39344:高知県大豊町:39363:高知県土佐町:39364:高知県大川村:39386:高知県いの町:39387:高知県仁淀川町:39401:高知県中土佐町:39402:高知県佐川町:39403:高知県越知町:39405:高知県梼原町:39410:高知県日高村:39411:高知県津野町:39412:高知県四万十町:39424:高知県大月町:39427:高知県三原村:39428:高知県黒潮町:40100:福岡県北九州市:40101:福岡県北九州市門司区:40103:福岡県北九州市若松区:40105:福岡県北九州市戸畑区:40106:福岡県北九州市小倉北区:40107:福岡県北九州市小倉南区:40108:福岡県北九州市八幡東区:40109:福岡県北九州市八幡西区:40130:福岡県福岡市:40131:福岡県福岡市東区:40132:福岡県福岡市博多区:40133:福岡県福岡市中央区:40134:福岡県福岡市南区:40135:福岡県福岡市西区:40136:福岡県福岡市城南区:40137:福岡県福岡市早良区:40202:福岡県大牟田市:40203:福岡県久留米市:40204:福岡県直方市:40205:福岡県飯塚市:40206:福岡県田川市:40207:福岡県柳川市:40210:福岡県八女市:40211:福岡県筑後市:40212:福岡県大川市:40213:福岡県行橋市:40214:福岡県豊前市:40215:福岡県中間市:40216:福岡県小郡市:40217:福岡県筑紫野市:40218:福岡県春日市:40219:福岡県大野城市:40220:福岡県宗像市:40221:福岡県太宰府市:40223:福岡県古賀市:40224:福岡県福津市:40225:福岡県うきは市:40226:福岡県宮若市:40227:福岡県嘉麻市:40228:福岡県朝倉市:40229:福岡県みやま市:40230:福岡県糸島市:40231:福岡県那珂川市:40341:福岡県宇美町:40342:福岡県篠栗町:40343:福岡県志免町:40344:福岡県須恵町:40345:福岡県新宮町:40348:福岡県久山町:40349:福岡県粕屋町:40381:福岡県芦屋町:40382:福岡県水巻町:40383:福岡県岡垣町:40384:福岡県遠賀町:40401:福岡県小竹町:40402:福岡県鞍手町:40421:福岡県桂川町:40447:福岡県筑前町:40448:福岡県東峰村:40503:福岡県大刀洗町:40522:福岡県大木町:40544:福岡県広川町:40601:福岡県香春町:40602:福岡県添田町:40604:福岡県糸田町:40605:福岡県川崎町:40608:福岡県大任町:40609:福岡県赤村:40610:福岡県福智町:40621:福岡県苅田町:40625:福岡県みやこ町:40642:福岡県吉富町:40646:福岡県上毛町:40647:福岡県築上町:41201:佐賀県佐賀市:41202:佐賀県唐津市:41203:佐賀県鳥栖市:41204:佐賀県多久市:41205:佐賀県伊万里市:41206:佐賀県武雄市:41207:佐賀県鹿島市:41208:佐賀県小城市:41209:佐賀県嬉野市:41210:佐賀県神埼市:41327:佐賀県吉野ヶ里町:41341:佐賀県基山町:41345:佐賀県上峰町:41346:佐賀県みやき町:41387:佐賀県玄海町:41401:佐賀県有田町:41423:佐賀県大町町:41424:佐賀県江北町:41425:佐賀県白石町:41441:佐賀県太良町:42201:長崎県長崎市:42202:長崎県佐世保市:42203:長崎県島原市:42204:長崎県諫早市:42205:長崎県大村市:42207:長崎県平戸市:42208:長崎県松浦市:42209:長崎県対馬市:42210:長崎県壱岐市:42211:長崎県五島市:42212:長崎県西海市:42213:長崎県雲仙市:42214:長崎県南島原市:42307:長崎県長与町:42308:長崎県時津町:42321:長崎県東彼杵町:42322:長崎県川棚町:42323:長崎県波佐見町:42383:長崎県小値賀町:42391:長崎県佐々町:42411:長崎県新上五島町:43100:熊本県熊本市:43101:熊本県熊本市中央区:43102:熊本県熊本市東区:43103:熊本県熊本市西区:43104:熊本県熊本市南区:43105:熊本県熊本市北区:43202:熊本県八代市:43203:熊本県人吉市:43204:熊本県荒尾市:43205:熊本県水俣市:43206:熊本県玉名市:43208:熊本県山鹿市:43210:熊本県菊池市:43211:熊本県宇土市:43212:熊本県上天草市:43213:熊本県宇城市:43214:熊本県阿蘇市:43215:熊本県天草市:43216:熊本県合志市:43348:熊本県美里町:43364:熊本県玉東町:43367:熊本県南関町:43368:熊本県長洲町:43369:熊本県和水町:43403:熊本県大津町:43404:熊本県菊陽町:43423:熊本県南小国町:43424:熊本県小国町:43425:熊本県産山村:43428:熊本県高森町:43432:熊本県西原村:43433:熊本県南阿蘇村:43441:熊本県御船町:43442:熊本県嘉島町:43443:熊本県益城町:43444:熊本県甲佐町:43447:熊本県山都町:43468:熊本県氷川町:43482:熊本県芦北町:43484:熊本県津奈木町:43501:熊本県錦町:43505:熊本県多良木町:43506:熊本県湯前町:43507:熊本県水上村:43510:熊本県相良村:43511:熊本県五木村:43512:熊本県山江村:43513:熊本県球磨村:43514:熊本県あさぎり町:43531:熊本県苓北町:44201:大分県大分市:44202:大分県別府市:44203:大分県中津市:44204:大分県日田市:44205:大分県佐伯市:44206:大分県臼杵市:44207:大分県津久見市:44208:大分県竹田市:44209:大分県豊後高田市:44210:大分県杵築市:44211:大分県宇佐市:44212:大分県豊後大野市:44213:大分県由布市:44214:大分県国東市:44322:大分県姫島村:44341:大分県日出町:44461:大分県九重町:44462:大分県玖珠町:45201:宮崎県宮崎市:45202:宮崎県都城市:45203:宮崎県延岡市:45204:宮崎県日南市:45205:宮崎県小林市:45206:宮崎県日向市:45207:宮崎県串間市:45208:宮崎県西都市:45209:宮崎県えびの市:45341:宮崎県三股町:45361:宮崎県高原町:45382:宮崎県国富町:45383:宮崎県綾町:45401:宮崎県高鍋町:45402:宮崎県新富町:45403:宮崎県西米良村:45404:宮崎県木城町:45405:宮崎県川南町:45406:宮崎県都農町:45421:宮崎県門川町:45429:宮崎県諸塚村:45430:宮崎県椎葉村:45431:宮崎県美郷町:45441:宮崎県高千穂町:45442:宮崎県日之影町:45443:宮崎県五ヶ瀬町:46201:鹿児島県鹿児島市:46203:鹿児島県鹿屋市:46204:鹿児島県枕崎市:46206:鹿児島県阿久根市:46208:鹿児島県出水市:46210:鹿児島県指宿市:46213:鹿児島県西之表市:46214:鹿児島県垂水市:46215:鹿児島県薩摩川内市:46216:鹿児島県日置市:46217:鹿児島県曽於市:46218:鹿児島県霧島市:46219:鹿児島県いちき串木野市:46220:鹿児島県南さつま市:46221:鹿児島県志布志市:46222:鹿児島県奄美市:46223:鹿児島県南九州市:46224:鹿児島県伊佐市:46225:鹿児島県姶良市:46303:鹿児島県三島村:46304:鹿児島県十島村:46392:鹿児島県さつま町:46404:鹿児島県長島町:46452:鹿児島県湧水町:46468:鹿児島県大崎町:46482:鹿児島県東串良町:46490:鹿児島県錦江町:46491:鹿児島県南大隅町:46492:鹿児島県肝付町:46501:鹿児島県中種子町:46502:鹿児島県南種子町:46505:鹿児島県屋久島町:46523:鹿児島県大和村:46524:鹿児島県宇検村:46525:鹿児島県瀬戸内町:46527:鹿児島県龍郷町:46529:鹿児島県喜界町:46530:鹿児島県徳之島町:46531:鹿児島県天城町:46532:鹿児島県伊仙町:46533:鹿児島県和泊町:46534:鹿児島県知名町:46535:鹿児島県与論町:47201:沖縄県那覇市:47205:沖縄県宜野湾市:47207:沖縄県石垣市:47208:沖縄県浦添市:47209:沖縄県名護市:47210:沖縄県糸満市:47211:沖縄県沖縄市:47212:沖縄県豊見城市:47213:沖縄県うるま市:47214:沖縄県宮古島市:47215:沖縄県南城市:47301:沖縄県国頭村:47302:沖縄県大宜味村:47303:沖縄県東村:47306:沖縄県今帰仁村:47308:沖縄県本部町:47311:沖縄県恩納村:47313:沖縄県宜野座村:47314:沖縄県金武町:47315:沖縄県伊江村:47324:沖縄県読谷村:47325:沖縄県嘉手納町:47326:沖縄県北谷町:47327:沖縄県北中城村:47328:沖縄県中城村:47329:沖縄県西原町:47348:沖縄県与那原町:47350:沖縄県南風原町:47353:沖縄県渡嘉敷村:47354:沖縄県座間味村:47355:沖縄県粟国村:47356:沖縄県渡名喜村:47357:沖縄県南大東村:47358:沖縄県北大東村:47359:沖縄県伊平屋村:47360:沖縄県伊是名村:47361:沖縄県久米島町:47362:沖縄県八重瀬町:47375:沖縄県多良間村:47381:沖縄県竹富町:47382:沖縄県与那国町), uro_landUseDetailAttribute_reference char(10), uro_landUseDetailAttribute_note char(50), uro_landUseDetailAttribute_surveyYear char(10), xml_genericAttributeSet char(10000)
lod1_LandUse (reader GEODATABASE_XML_1)
    attributes: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

Bookmark: Generic プロパティ
text_line (reader TEXTLINE_1)
    attributes: text_line_data buffer
    -> Sampler
